FME workspace calculo_altura_mds -FINAL.fmw

Parameters:
- SourceDataset_ESRISHAPE_4 = D:\repositorio_tcc_puc\dados\final\articulacao\edificacao_articulacao\EDIFICACAO.EDIFICACAO.shp   # Source Esri Shapefile(s)
- SourceDataset_XYZ = ""D:\repositorio_tcc_puc\dados\MDS\MDS_4243.xyz" "D:\repositorio_tcc_puc\dados\MDS\MDS_4244.xyz" "D:\repositorio_tcc_puc\dados\MDS\MDS_4245.xyz" "D:\repositorio_tcc_puc\dados\MDS\MDS_4341.xyz" "D:\repositorio_tcc_puc\dados\MDS\MDS_4342.xyz" "D:\repositorio_tcc_puc\dados\MDS\MDS_4343.xyz" "D:\repositorio_tcc_puc\dados\MDS\MDS_4344.xyz" "D:\repositorio_tcc_puc\dados\MDS\MDS_4345.xyz" "D:\repositorio_tcc_puc\dados\MDS\MDS_4439.xyz" "D:\repositorio_tcc_puc\dados\MDS\MDS_4440.xyz" "D:\repositorio_tcc_puc\dados\MDS\MDS_4441.xyz" "D:\repositorio_tcc_puc\dados\MDS\MDS_4442.xyz" "D:\repositorio_tcc_puc\dados\MDS\MDS_4443.xyz" "D:\repositorio_tcc_puc\dados\MDS\MDS_4444.xyz" "D:\repositorio_tcc_puc\dados\MDS\MDS_4538.xyz" "D:\repositorio_tcc_puc\dados\MDS\MDS_4539.xyz" "D:\repositorio_tcc_puc\dados\MDS\MDS_4540.xyz" "D:\repositorio_tcc_puc\dados\MDS\MDS_4541.xyz" "D:\repositorio_tcc_puc\dados\MDS\MDS_4542.xyz" "D:\repositorio_tcc_puc\dados\MDS\MDS_4543.xyz" "D:\repositorio_tcc_puc\dados\MDS\MDS_4544.xyz" "D:\repositorio_tcc_puc\dados\MDS\MDS_4545.xyz" "D:\repositorio_tcc_puc\dados\MDS\MDS_4548.xyz" "D:\repositorio_tcc_puc\dados\MDS\MDS_4549.xyz" "D:\repositorio_tcc_puc\dados\MDS\MDS_4550.xyz" "D:\repositorio_tcc_puc\dados\MDS\MDS_4551.xyz" "D:\repositorio_tcc_puc\dados\MDS\MDS_4552.xyz" "D:\repositorio_tcc_puc\dados\MDS\MDS_4553.xyz" "D:\repositorio_tcc_puc\dados\MDS\MDS_4556.xyz" "D:\repositorio_tcc_puc\dados\MDS\MDS_4557.xyz" "D:\repositorio_tcc_puc\dados\MDS\MDS_4635.xyz" "D:\repositorio_tcc_puc\dados\MDS\MDS_4636.xyz" "D:\repositorio_tcc_puc\dados\MDS\MDS_4637.xyz" "D:\repositorio_tcc_puc\dados\MDS\MDS_4638.xyz" "D:\repositorio_tcc_puc\dados\MDS\MDS_4639.xyz" "D:\repositorio_tcc_puc\dados\MDS\MDS_4640.xyz" "D:\repositorio_tcc_puc\dados\MDS\MDS_4641.xyz" "D:\repositorio_tcc_puc\dados\MDS\MDS_4642.xyz" "D:\repositorio_tcc_puc\dados\MDS\MDS_4643.xyz" "D:\repositorio_tcc_puc\dados\MDS\MDS_4644.xyz" "D:\repositorio_tcc_puc\dados\MDS\MDS_4645.xyz" "D:\repositorio_tcc_puc\dados\MDS\MDS_4646.xyz" "D:\repositorio_tcc_puc\dados\MDS\MDS_4647.xyz" "D:\repositorio_tcc_puc\dados\MDS\MDS_4648.xyz" "D:\repositorio_tcc_puc\dados\MDS\MDS_4649.xyz" "D:\repositorio_tcc_puc\dados\MDS\MDS_4650.xyz" "D:\repositorio_tcc_puc\dados\MDS\MDS_4651.xyz" "D:\repositorio_tcc_puc\dados\MDS\MDS_4652.xyz" "D:\repositorio_tcc_puc\dados\MDS\MDS_4653.xyz" "D:\repositorio_tcc_puc\dados\MDS\MDS_4654.xyz" "D:\repositorio_tcc_puc\dados\MDS\MDS_4655.xyz" "D:\repositorio_tcc_puc\dados\MDS\MDS_4656.xyz" "D:\repositorio_tcc_puc\dados\MDS\MDS_4657.xyz" "D:\repositorio_tcc_puc\dados\MDS\MDS_4658.xyz" "D:\repositorio_tcc_puc\dados\MDS\MDS_4659.xyz" "D:\repositorio_tcc_puc\dados\MDS\MDS_4660.xyz" "D:\repositorio_tcc_puc\dados\MDS\MDS_4661.xyz" "D:\repositorio_tcc_puc\dados\MDS\MDS_4662.xyz" "D:\repositorio_tcc_puc\dados\MDS\MDS_4735.xyz" "D:\repositorio_tcc_puc\dados\MDS\MDS_4736.xyz" "D:\repositorio_tcc_puc\dados\MDS\MDS_4737.xyz" "D:\repositorio_tcc_puc\dados\MDS\MDS_4738.xyz" "D:\repositorio_tcc_puc\dados\MDS\MDS_4739.xyz" "D:\repositorio_tcc_puc\dados\MDS\MDS_4740.xyz" "D:\repositorio_tcc_puc\dados\MDS\MDS_4741.xyz" "D:\repositorio_tcc_puc\dados\MDS\MDS_4742.xyz" "D:\repositorio_tcc_puc\dados\MDS\MDS_4743.xyz" "D:\repositorio_tcc_puc\dados\MDS\MDS_4744.xyz" "D:\repositorio_tcc_puc\dados\MDS\MDS_4745.xyz" "D:\repositorio_tcc_puc\dados\MDS\MDS_4746.xyz" "D:\repositorio_tcc_puc\dados\MDS\MDS_4747.xyz" "D:\repositorio_tcc_puc\dados\MDS\MDS_4748.xyz" "D:\repositorio_tcc_puc\dados\MDS\MDS_4749.xyz" "D:\repositorio_tcc_puc\dados\MDS\MDS_4750.xyz" "D:\repositorio_tcc_puc\dados\MDS\MDS_4751.xyz" "D:\repositorio_tcc_puc\dados\MDS\MDS_4752.xyz" "D:\repositorio_tcc_puc\dados\MDS\MDS_4753.xyz" "D:\repositorio_tcc_puc\dados\MDS\MDS_4754.xyz" "D:\repositorio_tcc_puc\dados\MDS\MDS_4755.xyz" "D:\repositorio_tcc_puc\dados\MDS\MDS_4756.xyz" "D:\repositorio_tcc_puc\dados\MDS\MDS_4757.xyz" "D:\repositorio_tcc_puc\dados\MDS\MDS_4758.xyz" "D:\repositorio_tcc_puc\dados\MDS\MDS_4759.xyz" "D:\repositorio_tcc_puc\dados\MDS\MDS_4760.xyz" "D:\repositorio_tcc_puc\dados\MDS\MDS_4761.xyz" "D:\repositorio_tcc_puc\dados\MDS\MDS_4762.xyz" "D:\repositorio_tcc_puc\dados\MDS\MDS_4763.xyz" "D:\repositorio_tcc_puc\dados\MDS\MDS_4764.xyz" "D:\repositorio_tcc_puc\dados\MDS\MDS_4837.xyz" "D:\repositorio_tcc_puc\dados\MDS\MDS_4838.xyz" "D:\repositorio_tcc_puc\dados\MDS\MDS_4839.xyz" "D:\repositorio_tcc_puc\dados\MDS\MDS_4840.xyz" "D:\repositorio_tcc_puc\dados\MDS\MDS_4841.xyz" "D:\repositorio_tcc_puc\dados\MDS\MDS_4842.xyz" "D:\repositorio_tcc_puc\dados\MDS\MDS_4843.xyz" "D:\repositorio_tcc_puc\dados\MDS\MDS_4844.xyz" "D:\repositorio_tcc_puc\dados\MDS\MDS_4845.xyz" "D:\repositorio_tcc_puc\dados\MDS\MDS_4846.xyz" "D:\repositorio_tcc_puc\dados\MDS\MDS_4847.xyz" "D:\repositorio_tcc_puc\dados\MDS\MDS_4848.xyz" "D:\repositorio_tcc_puc\dados\MDS\MDS_4849.xyz" "D:\repositorio_tcc_puc\dados\MDS\MDS_4850.xyz" "D:\repositorio_tcc_puc\dados\MDS\MDS_4851.xyz" "D:\repositorio_tcc_puc\dados\MDS\MDS_4852.xyz" "D:\repositorio_tcc_puc\dados\MDS\MDS_4853.xyz" "D:\repositorio_tcc_puc\dados\MDS\MDS_4854.xyz" "D:\repositorio_tcc_puc\dados\MDS\MDS_4855.xyz" "D:\repositorio_tcc_puc\dados\MDS\MDS_4856.xyz" "D:\repositorio_tcc_puc\dados\MDS\MDS_4857.xyz" "D:\repositorio_tcc_puc\dados\MDS\MDS_4858.xyz" "D:\repositorio_tcc_puc\dados\MDS\MDS_4859.xyz" "D:\repositorio_tcc_puc\dados\MDS\MDS_4860.xyz" "D:\repositorio_tcc_puc\dados\MDS\MDS_4861.xyz" "D:\repositorio_tcc_puc\dados\MDS\MDS_4862.xyz" "D:\repositorio_tcc_puc\dados\MDS\MDS_4863.xyz" "D:\repositorio_tcc_puc\dados\MDS\MDS_4864.xyz" "D:\repositorio_tcc_puc\dados\MDS\MDS_4865.xyz" "D:\repositorio_tcc_puc\dados\MDS\MDS_4866.xyz" "D:\repositorio_tcc_puc\dados\MDS\MDS_4939.xyz" "D:\repositorio_tcc_puc\dados\MDS\MDS_4940.xyz" "D:\repositorio_tcc_puc\dados\MDS\MDS_4941.xyz" "D:\repositorio_tcc_puc\dados\MDS\MDS_4942.xyz" "D:\repositorio_tcc_puc\dados\MDS\MDS_4943.xyz" "D:\repositorio_tcc_puc\dados\MDS\MDS_4944.xyz" "D:\repositorio_tcc_puc\dados\MDS\MDS_4945.xyz" "D:\repositorio_tcc_puc\dados\MDS\MDS_4946.xyz" "D:\repositorio_tcc_puc\dados\MDS\MDS_4947.xyz" "D:\repositorio_tcc_puc\dados\MDS\MDS_4948.xyz" "D:\repositorio_tcc_puc\dados\MDS\MDS_4949.xyz" "D:\repositorio_tcc_puc\dados\MDS\MDS_4950.xyz" "D:\repositorio_tcc_puc\dados\MDS\MDS_4951.xyz" "D:\repositorio_tcc_puc\dados\MDS\MDS_4952.xyz" "D:\repositorio_tcc_puc\dados\MDS\MDS_4953.xyz" "D:\repositorio_tcc_puc\dados\MDS\MDS_4954.xyz" "D:\repositorio_tcc_puc\dados\MDS\MDS_4955.xyz" "D:\repositorio_tcc_puc\dados\MDS\MDS_4956.xyz" "D:\repositorio_tcc_puc\dados\MDS\MDS_4957.xyz" "D:\repositorio_tcc_puc\dados\MDS\MDS_4958.xyz" "D:\repositorio_tcc_puc\dados\MDS\MDS_4959.xyz" "D:\repositorio_tcc_puc\dados\MDS\MDS_4960.xyz" "D:\repositorio_tcc_puc\dados\MDS\MDS_4961.xyz" "D:\repositorio_tcc_puc\dados\MDS\MDS_4962.xyz" "D:\repositorio_tcc_puc\dados\MDS\MDS_4963.xyz" "D:\repositorio_tcc_puc\dados\MDS\MDS_4964.xyz" "D:\repositorio_tcc_puc\dados\MDS\MDS_4965.xyz" "D:\repositorio_tcc_puc\dados\MDS\MDS_4966.xyz" "D:\repositorio_tcc_puc\dados\MDS\MDS_5041.xyz" "D:\repositorio_tcc_puc\dados\MDS\MDS_5042.xyz" "D:\repositorio_tcc_puc\dados\MDS\MDS_5043.xyz" "D:\repositorio_tcc_puc\dados\MDS\MDS_5044.xyz" "D:\repositorio_tcc_puc\dados\MDS\MDS_5045.xyz" "D:\repositorio_tcc_puc\dados\MDS\MDS_5046.xyz" "D:\repositorio_tcc_puc\dados\MDS\MDS_5047.xyz" "D:\repositorio_tcc_puc\dados\MDS\MDS_5048.xyz" "D:\repositorio_tcc_puc\dados\MDS\MDS_5049.xyz" "D:\repositorio_tcc_puc\dados\MDS\MDS_5050.xyz" "D:\repositorio_tcc_puc\dados\MDS\MDS_5051.xyz" "D:\repositorio_tcc_puc\dados\MDS\MDS_5052.xyz" "D:\repositorio_tcc_puc\dados\MDS\MDS_5053.xyz" "D:\repositorio_tcc_puc\dados\MDS\MDS_5054.xyz" "D:\repositorio_tcc_puc\dados\MDS\MDS_5055.xyz" "D:\repositorio_tcc_puc\dados\MDS\MDS_5056.xyz" "D:\repositorio_tcc_puc\dados\MDS\MDS_5057.xyz" "D:\repositorio_tcc_puc\dados\MDS\MDS_5058.xyz" "D:\repositorio_tcc_puc\dados\MDS\MDS_5059.xyz" "D:\repositorio_tcc_puc\dados\MDS\MDS_5060.xyz" "D:\repositorio_tcc_puc\dados\MDS\MDS_5061.xyz" "D:\repositorio_tcc_puc\dados\MDS\MDS_5062.xyz" "D:\repositorio_tcc_puc\dados\MDS\MDS_5063.xyz" "D:\repositorio_tcc_puc\dados\MDS\MDS_5064.xyz" "D:\repositorio_tcc_puc\dados\MDS\MDS_5065.xyz" "D:\repositorio_tcc_puc\dados\MDS\MDS_5066.xyz" "D:\repositorio_tcc_puc\dados\MDS\MDS_5141.xyz" "D:\repositorio_tcc_puc\dados\MDS\MDS_5142.xyz" "D:\repositorio_tcc_puc\dados\MDS\MDS_5143.xyz" "D:\repositorio_tcc_puc\dados\MDS\MDS_5144.xyz" "D:\repositorio_tcc_puc\dados\MDS\MDS_5145.xyz" "D:\repositorio_tcc_puc\dados\MDS\MDS_5146.xyz" "D:\repositorio_tcc_puc\dados\MDS\MDS_5147.xyz" "D:\repositorio_tcc_puc\dados\MDS\MDS_5148.xyz" "D:\repositorio_tcc_puc\dados\MDS\MDS_5149.xyz" "D:\repositorio_tcc_puc\dados\MDS\MDS_5150.xyz" "D:\repositorio_tcc_puc\dados\MDS\MDS_5151.xyz" "D:\repositorio_tcc_puc\dados\MDS\MDS_5152.xyz" "D:\repositorio_tcc_puc\dados\MDS\MDS_5153.xyz" "D:\repositorio_tcc_puc\dados\MDS\MDS_5154.xyz" "D:\repositorio_tcc_puc\dados\MDS\MDS_5155.xyz" "D:\repositorio_tcc_puc\dados\MDS\MDS_5156.xyz" "D:\repositorio_tcc_puc\dados\MDS\MDS_5157.xyz" "D:\repositorio_tcc_puc\dados\MDS\MDS_5158.xyz" "D:\repositorio_tcc_puc\dados\MDS\MDS_5159.xyz" "D:\repositorio_tcc_puc\dados\MDS\MDS_5160.xyz" "D:\repositorio_tcc_puc\dados\MDS\MDS_5161.xyz" "D:\repositorio_tcc_puc\dados\MDS\MDS_5162.xyz" "D:\repositorio_tcc_puc\dados\MDS\MDS_5163.xyz" "D:\repositorio_tcc_puc\dados\MDS\MDS_5164.xyz" "D:\repositorio_tcc_puc\dados\MDS\MDS_5165.xyz" "D:\repositorio_tcc_puc\dados\MDS\MDS_5166.xyz" "D:\repositorio_tcc_puc\dados\MDS\MDS_5167.xyz" "D:\repositorio_tcc_puc\dados\MDS\MDS_5243.xyz" "D:\repositorio_tcc_puc\dados\MDS\MDS_5244.xyz" "D:\repositorio_tcc_puc\dados\MDS\MDS_5245.xyz" "D:\repositorio_tcc_puc\dados\MDS\MDS_5246.xyz" "D:\repositorio_tcc_puc\dados\MDS\MDS_5247.xyz" "D:\repositorio_tcc_puc\dados\MDS\MDS_5248.xyz" "D:\repositorio_tcc_puc\dados\MDS\MDS_5249.xyz" "D:\repositorio_tcc_puc\dados\MDS\MDS_5250.xyz" "D:\repositorio_tcc_puc\dados\MDS\MDS_5251.xyz" "D:\repositorio_tcc_puc\dados\MDS\MDS_5252.xyz" "D:\repositorio_tcc_puc\dados\MDS\MDS_5253.xyz" "D:\repositorio_tcc_puc\dados\MDS\MDS_5254.xyz" "D:\repositorio_tcc_puc\dados\MDS\MDS_5255.xyz" "D:\repositorio_tcc_puc\dados\MDS\MDS_5256.xyz" "D:\repositorio_tcc_puc\dados\MDS\MDS_5257.xyz" "D:\repositorio_tcc_puc\dados\MDS\MDS_5258.xyz" "D:\repositorio_tcc_puc\dados\MDS\MDS_5259.xyz" "D:\repositorio_tcc_puc\dados\MDS\MDS_5260.xyz" "D:\repositorio_tcc_puc\dados\MDS\MDS_5261.xyz" "D:\repositorio_tcc_puc\dados\MDS\MDS_5262.xyz" "D:\repositorio_tcc_puc\dados\MDS\MDS_5263.xyz" "D:\repositorio_tcc_puc\dados\MDS\MDS_5264.xyz" "D:\repositorio_tcc_puc\dados\MDS\MDS_5265.xyz" "D:\repositorio_tcc_puc\dados\MDS\MDS_5266.xyz" "D:\repositorio_tcc_puc\dados\MDS\MDS_5267.xyz" "D:\repositorio_tcc_puc\dados\MDS\MDS_5344.xyz" "D:\repositorio_tcc_puc\dados\MDS\MDS_5345.xyz" "D:\repositorio_tcc_puc\dados\MDS\MDS_5346.xyz" "D:\repositorio_tcc_puc\dados\MDS\MDS_5347.xyz" "D:\repositorio_tcc_puc\dados\MDS\MDS_5348.xyz" "D:\repositorio_tcc_puc\dados\MDS\MDS_5349.xyz" "D:\repositorio_tcc_puc\dados\MDS\MDS_5350.xyz" "D:\repositorio_tcc_puc\dados\MDS\MDS_5351.xyz" "D:\repositorio_tcc_puc\dados\MDS\MDS_5352.xyz" "D:\repositorio_tcc_puc\dados\MDS\MDS_5353.xyz" "D:\repositorio_tcc_puc\dados\MDS\MDS_5354.xyz" "D:\repositorio_tcc_puc\dados\MDS\MDS_5355.xyz" "D:\repositorio_tcc_puc\dados\MDS\MDS_5356.xyz" "D:\repositorio_tcc_puc\dados\MDS\MDS_5357.xyz" "D:\repositorio_tcc_puc\dados\MDS\MDS_5358.xyz" "D:\repositorio_tcc_puc\dados\MDS\MDS_5359.xyz" "D:\repositorio_tcc_puc\dados\MDS\MDS_5360.xyz" "D:\repositorio_tcc_puc\dados\MDS\MDS_5361.xyz" "D:\repositorio_tcc_puc\dados\MDS\MDS_5362.xyz" "D:\repositorio_tcc_puc\dados\MDS\MDS_5363.xyz" "D:\repositorio_tcc_puc\dados\MDS\MDS_5364.xyz" "D:\repositorio_tcc_puc\dados\MDS\MDS_5445.xyz" "D:\repositorio_tcc_puc\dados\MDS\MDS_5446.xyz" "D:\repositorio_tcc_puc\dados\MDS\MDS_5447.xyz" "D:\repositorio_tcc_puc\dados\MDS\MDS_5448.xyz" "D:\repositorio_tcc_puc\dados\MDS\MDS_5449.xyz" "D:\repositorio_tcc_puc\dados\MDS\MDS_5450.xyz" "D:\repositorio_tcc_puc\dados\MDS\MDS_5451.xyz" "D:\repositorio_tcc_puc\dados\MDS\MDS_5452.xyz" "D:\repositorio_tcc_puc\dados\MDS\MDS_5453.xyz" "D:\repositorio_tcc_puc\dados\MDS\MDS_5454.xyz" "D:\repositorio_tcc_puc\dados\MDS\MDS_5455.xyz" "D:\repositorio_tcc_puc\dados\MDS\MDS_5456.xyz" "D:\repositorio_tcc_puc\dados\MDS\MDS_5457.xyz" "D:\repositorio_tcc_puc\dados\MDS\MDS_5458.xyz" "D:\repositorio_tcc_puc\dados\MDS\MDS_5459.xyz" "D:\repositorio_tcc_puc\dados\MDS\MDS_5460.xyz" "D:\repositorio_tcc_puc\dados\MDS\MDS_5461.xyz" "D:\repositorio_tcc_puc\dados\MDS\MDS_5462.xyz" "D:\repositorio_tcc_puc\dados\MDS\MDS_5463.xyz" "D:\repositorio_tcc_puc\dados\MDS\MDS_5464.xyz" "D:\repositorio_tcc_puc\dados\MDS\MDS_5545.xyz" "D:\repositorio_tcc_puc\dados\MDS\MDS_5546.xyz" "D:\repositorio_tcc_puc\dados\MDS\MDS_5547.xyz" "D:\repositorio_tcc_puc\dados\MDS\MDS_5548.xyz" "D:\repositorio_tcc_puc\dados\MDS\MDS_5549.xyz" "D:\repositorio_tcc_puc\dados\MDS\MDS_5550.xyz" "D:\repositorio_tcc_puc\dados\MDS\MDS_5551.xyz" "D:\repositorio_tcc_puc\dados\MDS\MDS_5552.xyz" "D:\repositorio_tcc_puc\dados\MDS\MDS_5553.xyz" "D:\repositorio_tcc_puc\dados\MDS\MDS_5554.xyz" "D:\repositorio_tcc_puc\dados\MDS\MDS_5555.xyz" "D:\repositorio_tcc_puc\dados\MDS\MDS_5556.xyz" "D:\repositorio_tcc_puc\dados\MDS\MDS_5557.xyz" "D:\repositorio_tcc_puc\dados\MDS\MDS_5558.xyz" "D:\repositorio_tcc_puc\dados\MDS\MDS_5559.xyz" "D:\repositorio_tcc_puc\dados\MDS\MDS_5560.xyz" "D:\repositorio_tcc_puc\dados\MDS\MDS_5561.xyz" "D:\repositorio_tcc_puc\dados\MDS\MDS_5562.xyz" "D:\repositorio_tcc_puc\dados\MDS\MDS_5563.xyz" "D:\repositorio_tcc_puc\dados\MDS\MDS_5564.xyz" "D:\repositorio_tcc_puc\dados\MDS\MDS_5646.xyz" "D:\repositorio_tcc_puc\dados\MDS\MDS_5647.xyz" "D:\repositorio_tcc_puc\dados\MDS\MDS_5648.xyz" "D:\repositorio_tcc_puc\dados\MDS\MDS_5649.xyz" "D:\repositorio_tcc_puc\dados\MDS\MDS_5650.xyz" "D:\repositorio_tcc_puc\dados\MDS\MDS_5651.xyz" "D:\repositorio_tcc_puc\dados\MDS\MDS_5652.xyz" "D:\repositorio_tcc_puc\dados\MDS\MDS_5653.xyz" "D:\repositorio_tcc_puc\dados\MDS\MDS_5654.xyz" "D:\repositorio_tcc_puc\dados\MDS\MDS_5655.xyz" "D:\repositorio_tcc_puc\dados\MDS\MDS_5656.xyz" "D:\repositorio_tcc_puc\dados\MDS\MDS_5657.xyz" "D:\repositorio_tcc_puc\dados\MDS\MDS_5658.xyz" "D:\repositorio_tcc_puc\dados\MDS\MDS_5659.xyz" "D:\repositorio_tcc_puc\dados\MDS\MDS_5660.xyz" "D:\repositorio_tcc_puc\dados\MDS\MDS_5661.xyz" "D:\repositorio_tcc_puc\dados\MDS\MDS_5662.xyz" "D:\repositorio_tcc_puc\dados\MDS\MDS_5663.xyz" "D:\repositorio_tcc_puc\dados\MDS\MDS_5664.xyz" "D:\repositorio_tcc_puc\dados\MDS\MDS_5747.xyz" "D:\repositorio_tcc_puc\dados\MDS\MDS_5748.xyz" "D:\repositorio_tcc_puc\dados\MDS\MDS_5749.xyz" "D:\repositorio_tcc_puc\dados\MDS\MDS_5750.xyz" "D:\repositorio_tcc_puc\dados\MDS\MDS_5751.xyz" "D:\repositorio_tcc_puc\dados\MDS\MDS_5752.xyz" "D:\repositorio_tcc_puc\dados\MDS\MDS_5753.xyz" "D:\repositorio_tcc_puc\dados\MDS\MDS_5754.xyz" "D:\repositorio_tcc_puc\dados\MDS\MDS_5755.xyz" "D:\repositorio_tcc_puc\dados\MDS\MDS_5756.xyz" "D:\repositorio_tcc_puc\dados\MDS\MDS_5757.xyz" "D:\repositorio_tcc_puc\dados\MDS\MDS_5758.xyz" "D:\repositorio_tcc_puc\dados\MDS\MDS_5759.xyz" "D:\repositorio_tcc_puc\dados\MDS\MDS_5760.xyz" "D:\repositorio_tcc_puc\dados\MDS\MDS_5761.xyz" "D:\repositorio_tcc_puc\dados\MDS\MDS_5762.xyz" "D:\repositorio_tcc_puc\dados\MDS\MDS_5763.xyz" "D:\repositorio_tcc_puc\dados\MDS\MDS_5848.xyz" "D:\repositorio_tcc_puc\dados\MDS\MDS_5849.xyz" "D:\repositorio_tcc_puc\dados\MDS\MDS_5850.xyz" "D:\repositorio_tcc_puc\dados\MDS\MDS_5851.xyz" "D:\repositorio_tcc_puc\dados\MDS\MDS_5852.xyz" "D:\repositorio_tcc_puc\dados\MDS\MDS_5853.xyz" "D:\repositorio_tcc_puc\dados\MDS\MDS_5856.xyz" "D:\repositorio_tcc_puc\dados\MDS\MDS_5857.xyz" "D:\repositorio_tcc_puc\dados\MDS\MDS_5858.xyz" "D:\repositorio_tcc_puc\dados\MDS\MDS_5859.xyz" "D:\repositorio_tcc_puc\dados\MDS\MDS_5860.xyz" "D:\repositorio_tcc_puc\dados\MDS\MDS_5861.xyz" "D:\repositorio_tcc_puc\dados\MDS\MDS_5862.xyz" "D:\repositorio_tcc_puc\dados\MDS\MDS_5863.xyz" "D:\repositorio_tcc_puc\dados\MDS\MDS_5949.xyz" "D:\repositorio_tcc_puc\dados\MDS\MDS_5950.xyz" "D:\repositorio_tcc_puc\dados\MDS\MDS_5951.xyz" "D:\repositorio_tcc_puc\dados\MDS\MDS_5957.xyz" "D:\repositorio_tcc_puc\dados\MDS\MDS_5958.xyz" "D:\repositorio_tcc_puc\dados\MDS\MDS_5959.xyz" "D:\repositorio_tcc_puc\dados\MDS\MDS_5960.xyz" "D:\repositorio_tcc_puc\dados\MDS\MDS_5961.xyz" "D:\repositorio_tcc_puc\dados\MDS\MDS_5962.xyz" "D:\repositorio_tcc_puc\dados\MDS\MDS_6057.xyz" "D:\repositorio_tcc_puc\dados\MDS\MDS_6058.xyz" "D:\repositorio_tcc_puc\dados\MDS\MDS_6061.xyz""   # Space Delimited XYZ File(s)
- FEATURE_TYPES =
- DestDataset_ESRISHAPE =   # Destination Esri Shapefile Folder

Readers:
- ESRISHAPE_1: ESRISHAPE from $(SourceDataset_ESRISHAPE_4)
- XYZ_1: XYZ from $(SourceDataset_XYZ)

Writers:
- ESRISHAPE_2: ESRISHAPE to $(DestDataset_ESRISHAPE)

Note: Leitura do diretório
Trackline (reader XYZ_1)
    -> FeatureReader_2 [INITIATOR]
Note: Leitura dos arquivos MDS
FeatureReader_2
    ATTR_ACCUM_MODE = Only Use Result
    COMBINE_GEOM = Use Result
    DATASET = @Value(fme_dataset)
    FORMAT = XYZ
    INTERACT = <No Spatial Filter>
    MAX_FEATURES = 10
    OUTPUT_FEATURES_DISPLAY = Schema and Data Features
    XYZ_USE_SEARCH_ENVELOPE = NO
    XYZ_XYZ_EXPOSE_FORMAT_ATTRS = fme_basename,fme_char(50) fme_color,fme_char(50) fme_dataset,fme_char(50) fme_feature_type,fme_char(50) fme_fill_color,fme_char(50) fme_primary_axis,fme_real64 fme_rotation,fme_real64 fme_secondary_axis,fme_real64 fme_start_angle,fme_real64 fme_sweep_angle,fme_real64 fme_text_size,fme_real64 fme_text_string,fme_char(50) fme_type,fme_char(50) multi_reader_full_id,fme_int32 multi_reader_id,fme_int32 multi_reader_keyword,fme_char(50) multi_reader_type,fme_char(50) xyz_type,char(64)
    <OTHER> -> GeometryExtractor
Note: Extrair a geometria
GeometryExtractor
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> AttributeManager_2
Note: Criar atributo ARTICUlacao
AttributeManager_2
    ATTR_TABLE = SET_TO ARTICULACAO
    -> PythonCaller_2
Note: Setar o campo articulacao
PythonCaller_2
    PYTHONSOURCE:
      import fme
      import fmeobjects
      # Template Function interface:
      # When using this function, make sure its name is set as the value of
      # the 'Class or Function to Process Features' transformer parameter
      def processFeature(feature):
          pass

      # Percorrer o _relationships  e somar os id_ponto_onibus para gera um identificador
      class FeatureProcessor(object):
          def __init__(self):
              pass
          def input(self,feature):
              #percorrer o _relationships e buscar todos os ID_PONTO_ONIBUS somando
              # essa soma gera o IDENTIFICADOR_PONTO_ONIBUS
              feature.setAttribute("ARTICULACAO", feature.getAttribute('fme_basename'))  #IDENTIFICADOR_PONTO_ONIBUS
              self.pyoutput(feature)
          def close(self):
              pass
    PYTHONSYMBOL = FeatureProcessor
    -> CoordinateExtractor
Note: Extrair o a coordenada z
CoordinateExtractor
    IND = 0
    LIST_NAME = _indices
    MODE = All Coordinates
    X_ATTR = _x
    Y_ATTR = _y
    Z_ATTR = _z
    -> AttributeFilter_3
Note: Filtro das articulações
AttributeFilter_3
    ATTR_NAME = ARTICULACAO
    ATTR_VALUES = <Empty>,<Missing>,<Null>,<Unfiltered>,5151,5146,4243,4244,4245,4341,4342,4343,4344,4345,4439,4440,4441,4442,4443,4444,4538,4539,4540,4541,4542,4543,4544,4545,4548,4549,4550,4551,4552,4553,4556,4557,4635,4636,4637,4638,4639,4640,4641,4642,4643,4644,4645,4646,4647,4648,4649,4650,4651,4652,4653,4654,4655,4656,4657,4658,4659,4660,4661,4662,4735,4736,4737,4738,4739,4740,4741,4742,4743,4744,4745,4746,4747,4748,4749,4750,4751,4752,4753,4754,4755,4756,4757,4758,4759,4760,4761,4762,4763,4764,4837,4838,4839,4840,4841,4842,4843,4844,4845,4846,4847,4848,4849,4850,4851,4852,4853,4854,4855,4856,4857,4858,4859,4860,4861,4862,4863,4864,4865,4866,4939,4940,4941,4942,4943,4944,4945,4946,4947,4948,4949,4950,4951,4952,4953,4954,4955,4956,4957,4958,4959,4960,4961,4962,4963,4964,4965,4966,5041,5042,5043,5044,5045,5046,5047,5048,5049,5050,5051,5052,5053,5054,5055,5056,5057,5058,5059,5060,5061,5062,5063,5064,5065,5066,5141,5142,5143,5144,5145,5146,5147,5148,5149,5150,5151,5152,5153,5154,5155,5156,5157,5158,5159,5160,5161,5162,5163,5164,5165,5166,5167,5243,5244,5245,5246,5247,5248,5249,5250,5251,5252,5253,5254,5255,5256,5257,5258,5259,5260,5261,5262,5263,5264,5265,5266,5267,5344,5345,5346,5347,5348,5349,5350,5351,5352,5353,5354,5355,5356,5357,5358,5359,5360,5361,5362,5363,5364,5445,5446,5447,5448,5449,5450,5451,5452,5453,5454,5455,5456,5457,5458,5459,5460,5461,5462,5463,5464,5545,5546,5547,5548,5549,5550,5551,5552,5553,5554,5555,5556,5557,5558,5559,5560,5561,5562,5563,5564,5646,5647,5648,5649,5650,5651,5652,5653,5654,5655,5656,5657,5658,5659,5660,5661,5662,5663,5664,5747,5748,5749,5750,5751,5752,5753,5754,5755,5756,5757,5758,5759,5760,5761,5762,5763,5848,5849,5850,5851,5852,5853,5856,5857,5858,5859,5860,5861,5862,5863,5949,5950,5951,5957,5958,5959,5960,5961,5962,6057,6058,6061
    5151 -> Transformador_01 [SpatialRelator_Supplier]
    5151 -> Transformador_05 [SpatialRelator_16_Supplier_5]
    5146 -> Transformador_01 [SpatialRelator_2_Supplier]
    5146 -> Transformador_05 [SpatialRelator_11_Supplier_6]
    4243 -> Transformador_01 [SpatialRelator_3_Supplier]
    4244 -> Transformador_01 [SpatialRelator_4_Supplier]
    4245 -> Transformador_01 [SpatialRelator_5_Supplier]
    4341 -> Transformador_01 [SpatialRelator_6_Supplier]
    4342 -> Transformador_01 [SpatialRelator_7_Supplier]
    4343 -> Transformador_01 [SpatialRelator_8_Supplier]
    4344 -> Transformador_01 [SpatialRelator_9_Supplier]
    4345 -> Transformador_01 [SpatialRelator_10_Supplier]
    4439 -> Transformador_01 [SpatialRelator_11_Supplier]
    4440 -> Transformador_01 [SpatialRelator_12_Supplier]
    4441 -> Transformador_01 [SpatialRelator_13_Supplier]
    4442 -> Transformador_01 [SpatialRelator_14_Supplier]
    4443 -> Transformador_02 [SpatialRelator_7_Supplier_1]
    4444 -> Transformador_02 [SpatialRelator_2_Supplier_1]
    4538 -> Transformador_02 [SpatialRelator_3_Supplier_1]
    4539 -> Transformador_02 [SpatialRelator_4_Supplier_1]
    4540 -> Transformador_02 [SpatialRelator_5_Supplier_1]
    4541 -> Transformador_02 [SpatialRelator_6_Supplier_1]
    4542 -> Transformador_02 [SpatialRelator_9_Supplier_1]
    4543 -> Transformador_02 [SpatialRelator_10_Supplier_1]
    4544 -> Transformador_02 [SpatialRelator_11_Supplier_1]
    4545 -> Transformador_02 [SpatialRelator_12_Supplier_1]
    4548 -> Transformador_02 [SpatialRelator_13_Supplier_1]
    4549 -> Transformador_02 [SpatialRelator_14_Supplier_1]
    4550 -> Transformador_02 [SpatialRelator_15_Supplier]
    4551 -> Transformador_02 [SpatialRelator_16_Supplier]
    4552 -> Transformador_02 [SpatialRelator_17_Supplier]
    4553 -> Transformador_02 [SpatialRelator_18_Supplier]
    4556 -> Transformador_02 [SpatialRelator_19_Supplier]
    4557 -> Transformador_02 [SpatialRelator_20_Supplier]
    4635 -> Transformador_02 [SpatialRelator_21_Supplier]
    4636 -> Transformador_03 [SpatialRelator_8_Supplier_1]
    4637 -> Transformador_03 [SpatialRelator_3_Supplier_2]
    4638 -> Transformador_03 [SpatialRelator_4_Supplier_2]
    4639 -> Transformador_03 [SpatialRelator_5_Supplier_2]
    4640 -> Transformador_03 [SpatialRelator_6_Supplier_2]
    4641 -> Transformador_03 [SpatialRelator_7_Supplier_2]
    4642 -> Transformador_03 [SpatialRelator_9_Supplier_2]
    4643 -> Transformador_03 [SpatialRelator_10_Supplier_2]
    4644 -> Transformador_03 [SpatialRelator_11_Supplier_2]
    4645 -> Transformador_03 [SpatialRelator_12_Supplier_2]
    4646 -> Transformador_03 [SpatialRelator_13_Supplier_2]
    4647 -> Transformador_03 [SpatialRelator_25_Supplier]
    4648 -> Transformador_03 [SpatialRelator_14_Supplier_2]
    4649 -> Transformador_03 [SpatialRelator_15_Supplier_1]
    4650 -> Transformador_03 [SpatialRelator_16_Supplier_1]
    4651 -> Transformador_03 [SpatialRelator_17_Supplier_1]
    4652 -> Transformador_03 [SpatialRelator_18_Supplier_1]
    4653 -> Transformador_03 [SpatialRelator_24_Supplier]
    4654 -> Transformador_03 [SpatialRelator_19_Supplier_1]
    4655 -> Transformador_03 [SpatialRelator_20_Supplier_1]
    4656 -> Transformador_03 [SpatialRelator_21_Supplier_1]
    4657 -> Transformador_03 [SpatialRelator_22_Supplier]
    4658 -> Transformador_03 [SpatialRelator_23_Supplier]
    4659 -> Transformador_03 [SpatialRelator_26_Supplier]
    4660 -> Transformador_2 [SpatialRelator_11_Supplier_3]
    4661 -> Transformador_2 [SpatialRelator_3_Supplier_3]
    4662 -> Transformador_2 [SpatialRelator_4_Supplier_3]
    4735 -> Transformador_2 [SpatialRelator_5_Supplier_3]
    4736 -> Transformador_2 [SpatialRelator_9_Supplier_3]
    4737 -> Transformador_2 [SpatialRelator_6_Supplier_3]
    4738 -> Transformador_2 [SpatialRelator_7_Supplier_3]
    4739 -> Transformador_2 [SpatialRelator_8_Supplier_2]
    4740 -> Transformador_2 [SpatialRelator_14_Supplier_3]
    4741 -> Transformador_2 [SpatialRelator_10_Supplier_3]
    4742 -> Transformador_2 [SpatialRelator_12_Supplier_3]
    4743 -> Transformador_2 [SpatialRelator_13_Supplier_3]
    4744 -> Transformador_2 [SpatialRelator_18_Supplier_2]
    4745 -> Transformador_2 [SpatialRelator_15_Supplier_2]
    4746 -> Transformador_2 [SpatialRelator_16_Supplier_2]
    4746 -> Transformador_3 [SpatialRelator_16_Supplier_3]
    4747 -> Transformador_2 [SpatialRelator_17_Supplier_2]
    4748 -> Transformador_2 [SpatialRelator_22_Supplier_1]
    4749 -> Transformador_2 [SpatialRelator_19_Supplier_2]
    4750 -> Transformador_2 [SpatialRelator_20_Supplier_2]
    4751 -> Transformador_2 [SpatialRelator_21_Supplier_2]
    4752 -> Transformador_2 [SpatialRelator_23_Supplier_1]
    4753 -> Transformador_2 [SpatialRelator_24_Supplier_1]
    4754 -> Transformador_2 [SpatialRelator_26_Supplier_1]
    4755 -> Transformador_2 [SpatialRelator_25_Supplier_1]
    4756 -> Transformador_2 [SpatialRelator_27_Supplier]
    4756 -> Transformador_3 [SpatialRelator_16_Supplier_3]
    4757 -> Transformador_2 [SpatialRelator_28_Supplier]
    4758 -> Transformador_2 [SpatialRelator_30_Supplier]
    4759 -> Transformador_2 [SpatialRelator_29_Supplier]
    4760 -> Transformador_2 [SpatialRelator_31_Supplier]
    4761 -> Transformador_2 [SpatialRelator_32_Supplier]
    4762 -> Transformador_2 [SpatialRelator_34_Supplier]
    4762 -> Transformador_3 [SpatialRelator_16_Supplier_3]
    4763 -> Transformador_3 [SpatialRelator_28_Supplier_1]
    4764 -> Transformador_3 [SpatialRelator_29_Supplier_1]
    4837 -> Transformador_3 [SpatialRelator_30_Supplier_1]
    4838 -> Transformador_3 [SpatialRelator_3_Supplier_4]
    4839 -> Transformador_3 [SpatialRelator_4_Supplier_4]
    4840 -> Transformador_3 [SpatialRelator_5_Supplier_4]
    4841 -> Transformador_3 [SpatialRelator_6_Supplier_4]
    4842 -> Transformador_3 [SpatialRelator_7_Supplier_4]
    4843 -> Transformador_3 [SpatialRelator_8_Supplier_3]
    4844 -> Transformador_3 [SpatialRelator_9_Supplier_4]
    4845 -> Transformador_3 [SpatialRelator_10_Supplier_4]
    4846 -> Transformador_3 [SpatialRelator_11_Supplier_4]
    4847 -> Transformador_3 [SpatialRelator_12_Supplier_4]
    4848 -> Transformador_3 [SpatialRelator_13_Supplier_4]
    4849 -> Transformador_3 [SpatialRelator_14_Supplier_4]
    4850 -> Transformador_3 [SpatialRelator_15_Supplier_3]
    4851 -> Transformador_3 [SpatialRelator_16_Supplier_3]
    4852 -> Transformador_3 [SpatialRelator_17_Supplier_3]
    4853 -> Transformador_3 [SpatialRelator_18_Supplier_3]
    4854 -> Transformador_3 [SpatialRelator_19_Supplier_3]
    4855 -> Transformador_3 [SpatialRelator_20_Supplier_3]
    4856 -> Transformador_3 [SpatialRelator_21_Supplier_3]
    4857 -> Transformador_3 [SpatialRelator_22_Supplier_2]
    4858 -> Transformador_3 [SpatialRelator_32_Supplier_1]
    4859 -> Transformador_3 [SpatialRelator_34_Supplier_1]
    4860 -> Transformador_3 [SpatialRelator_23_Supplier_2]
    4861 -> Transformador_3 [SpatialRelator_24_Supplier_2]
    4862 -> Transformador_3 [SpatialRelator_25_Supplier_2]
    4863 -> Transformador_3 [SpatialRelator_26_Supplier_2]
    4864 -> Transformador_3 [SpatialRelator_27_Supplier_1]
    4865 -> Transformador_3 [SpatialRelator_31_Supplier_1]
    4866 -> Transformador_3 [SpatialRelator_33_Supplier_1]
    4939 -> Transformador_3 [SpatialRelator_35_Supplier]
    4940 -> Transformador_4 [SpatialRelator_3_Supplier_5]
    4941 -> Transformador_4 [SpatialRelator_4_Supplier_5]
    4942 -> Transformador_4 [SpatialRelator_5_Supplier_5]
    4943 -> Transformador_4 [SpatialRelator_6_Supplier_5]
    4944 -> Transformador_4 [SpatialRelator_7_Supplier_5]
    4945 -> Transformador_4 [SpatialRelator_8_Supplier_4]
    4946 -> Transformador_4 [SpatialRelator_9_Supplier_5]
    4947 -> Transformador_4 [SpatialRelator_10_Supplier_5]
    4948 -> Transformador_4 [SpatialRelator_11_Supplier_5]
    4949 -> Transformador_4 [SpatialRelator_12_Supplier_5]
    4950 -> Transformador_4 [SpatialRelator_13_Supplier_5]
    4951 -> Transformador_4 [SpatialRelator_14_Supplier_5]
    4952 -> Transformador_4 [SpatialRelator_15_Supplier_4]
    4953 -> Transformador_4 [SpatialRelator_16_Supplier_4]
    4954 -> Transformador_4 [SpatialRelator_17_Supplier_4]
    4955 -> Transformador_4 [SpatialRelator_18_Supplier_4]
    4956 -> Transformador_4 [SpatialRelator_19_Supplier_4]
    4957 -> Transformador_4 [SpatialRelator_20_Supplier_4]
    4958 -> Transformador_4 [SpatialRelator_22_Supplier_3]
    4959 -> Transformador_4 [SpatialRelator_21_Supplier_4]
    4960 -> Transformador_4 [SpatialRelator_23_Supplier_3]
    4961 -> Transformador_4 [SpatialRelator_24_Supplier_3]
    4962 -> Transformador_4 [SpatialRelator_25_Supplier_3]
    4963 -> Transformador_4 [SpatialRelator_26_Supplier_3]
    4964 -> Transformador_4 [SpatialRelator_27_Supplier_2]
    4965 -> Transformador_4 [SpatialRelator_29_Supplier_2]
    4966 -> Transformador_4 [SpatialRelator_28_Supplier_2]
    5041 -> Transformador_4 [SpatialRelator_44_Supplier]
    5042 -> Transformador_4 [SpatialRelator_46_Supplier]
    5043 -> Transformador_4 [SpatialRelator_45_Supplier]
    5044 -> Transformador_4 [SpatialRelator_30_Supplier_2]
    5045 -> Transformador_4 [SpatialRelator_31_Supplier_2]
    5046 -> Transformador_4 [SpatialRelator_32_Supplier_2]
    5047 -> Transformador_4 [SpatialRelator_33_Supplier_2]
    5048 -> Transformador_4 [SpatialRelator_34_Supplier_2]
    5049 -> Transformador_4 [SpatialRelator_36_Supplier]
    5050 -> Transformador_4 [SpatialRelator_35_Supplier_1]
    5051 -> Transformador_4 [SpatialRelator_47_Supplier]
    5052 -> Transformador_4 [SpatialRelator_49_Supplier]
    5053 -> Transformador_4 [SpatialRelator_48_Supplier]
    5054 -> Transformador_4 [SpatialRelator_37_Supplier]
    5055 -> Transformador_4 [SpatialRelator_38_Supplier]
    5056 -> Transformador_4 [SpatialRelator_39_Supplier]
    5057 -> Transformador_4 [SpatialRelator_40_Supplier]
    5058 -> Transformador_4 [SpatialRelator_41_Supplier]
    5059 -> Transformador_4 [SpatialRelator_43_Supplier]
    5060 -> Transformador_4 [SpatialRelator_42_Supplier]
    5061 -> Transformador_4 [SpatialRelator_50_Supplier]
    5062 -> Transformador_4 [SpatialRelator_52_Supplier]
    5063 -> Transformador_4 [SpatialRelator_51_Supplier]
    5064 -> Transformador_05 [SpatialRelator_3_Supplier_6]
    5065 -> Transformador_05 [SpatialRelator_4_Supplier_6]
    5066 -> Transformador_05 [SpatialRelator_5_Supplier_6]
    5141 -> Transformador_05 [SpatialRelator_6_Supplier_6]
    5142 -> Transformador_05 [SpatialRelator_7_Supplier_6]
    5143 -> Transformador_05 [SpatialRelator_8_Supplier_5]
    5144 -> Transformador_05 [SpatialRelator_9_Supplier_6]
    5145 -> Transformador_05 [SpatialRelator_10_Supplier_6]
    5147 -> Transformador_05 [SpatialRelator_12_Supplier_6]
    5148 -> Transformador_05 [SpatialRelator_13_Supplier_6]
    5149 -> Transformador_05 [SpatialRelator_14_Supplier_6]
    5150 -> Transformador_05 [SpatialRelator_15_Supplier_5]
    5152 -> Transformador_05 [SpatialRelator_17_Supplier_5]
    5153 -> Transformador_05 [SpatialRelator_18_Supplier_5]
    5154 -> Transformador_05 [SpatialRelator_19_Supplier_5]
    5155 -> Transformador_05 [SpatialRelator_20_Supplier_5]
    5156 -> Transformador_05 [SpatialRelator_21_Supplier_5]
    5157 -> Transformador_05 [SpatialRelator_22_Supplier_4]
    5158 -> Transformador_05 [SpatialRelator_23_Supplier_4]
    5159 -> Transformador_05 [SpatialRelator_24_Supplier_4]
    5160 -> Transformador_05 [SpatialRelator_25_Supplier_4]
    5161 -> Transformador_05 [SpatialRelator_26_Supplier_4]
    5162 -> Transformador_05 [SpatialRelator_27_Supplier_3]
    5163 -> Transformador_05 [SpatialRelator_28_Supplier_3]
    5164 -> Transformador_05 [SpatialRelator_29_Supplier_3]
    5165 -> Transformador_05 [SpatialRelator_30_Supplier_3]
    5166 -> Transformador_05 [SpatialRelator_31_Supplier_3]
    5167 -> Transformador_05 [SpatialRelator_32_Supplier_3]
    5243 -> Transformador_05 [SpatialRelator_33_Supplier_3]
    5244 -> Transformador_05 [SpatialRelator_34_Supplier_3]
    5245 -> Transformador_05 [SpatialRelator_35_Supplier_2]
    5246 -> Transformador_05 [SpatialRelator_36_Supplier_1]
    5247 -> Transformador_05 [SpatialRelator_37_Supplier_1]
    5248 -> Transformador_05 [SpatialRelator_38_Supplier_1]
    5249 -> Transformador_05 [SpatialRelator_39_Supplier_1]
    5250 -> Transformador_05 [SpatialRelator_40_Supplier_1]
    5251 -> Transformador_05 [SpatialRelator_41_Supplier_1]
    5252 -> Transformador_05 [SpatialRelator_42_Supplier_1]
    5253 -> Transformador_05 [SpatialRelator_43_Supplier_1]
    5254 -> Transformador_05 [SpatialRelator_44_Supplier_1]
    5255 -> Transformador_05 [SpatialRelator_45_Supplier_1]
    5256 -> Transformador_05 [SpatialRelator_46_Supplier_1]
    5257 -> Transformador_05 [SpatialRelator_47_Supplier_1]
    5258 -> Transformador_05 [SpatialRelator_48_Supplier_1]
    5259 -> Transformador_05 [SpatialRelator_49_Supplier_1]
    5260 -> Transformador_05 [SpatialRelator_50_Supplier_1]
    5261 -> Transformador_05 [SpatialRelator_51_Supplier_1]
    5262 -> Transformador_05 [SpatialRelator_52_Supplier_1]
    5263 -> Trasnformador_06 [SpatialRelator_3_Supplier_7]
    5264 -> Trasnformador_06 [SpatialRelator_4_Supplier_7]
    5265 -> Trasnformador_06 [SpatialRelator_5_Supplier_7]
    5266 -> Trasnformador_06 [SpatialRelator_6_Supplier_7]
    5267 -> Trasnformador_06 [SpatialRelator_7_Supplier_7]
    5344 -> Trasnformador_06 [SpatialRelator_8_Supplier_6]
    5345 -> Trasnformador_06 [SpatialRelator_9_Supplier_7]
    5346 -> Trasnformador_06 [SpatialRelator_10_Supplier_7]
    5347 -> Trasnformador_06 [SpatialRelator_11_Supplier_7]
    5348 -> Trasnformador_06 [SpatialRelator_12_Supplier_7]
    5349 -> Trasnformador_06 [SpatialRelator_13_Supplier_7]
    5350 -> Trasnformador_06 [SpatialRelator_14_Supplier_7]
    5351 -> Trasnformador_06 [SpatialRelator_15_Supplier_6]
    5352 -> Trasnformador_06 [SpatialRelator_16_Supplier_6]
    5353 -> Trasnformador_06 [SpatialRelator_17_Supplier_6]
    5354 -> Trasnformador_06 [SpatialRelator_18_Supplier_6]
    5355 -> Trasnformador_06 [SpatialRelator_19_Supplier_6]
    5356 -> Trasnformador_06 [SpatialRelator_20_Supplier_6]
    5357 -> Trasnformador_06 [SpatialRelator_21_Supplier_6]
    5358 -> Trasnformador_06 [SpatialRelator_23_Supplier_5]
    5359 -> Trasnformador_06 [SpatialRelator_24_Supplier_5]
    5360 -> Trasnformador_06 [SpatialRelator_25_Supplier_5]
    5361 -> Trasnformador_06 [SpatialRelator_26_Supplier_5]
    5362 -> Trasnformador_06 [SpatialRelator_27_Supplier_4]
    5363 -> Trasnformador_06 [SpatialRelator_28_Supplier_4]
    5364 -> Trasnformador_06 [SpatialRelator_29_Supplier_4]
    5445 -> Trasnformador_06 [SpatialRelator_30_Supplier_4]
    5446 -> Trasnformador_06 [SpatialRelator_31_Supplier_4]
    5447 -> Trasnformador_06 [SpatialRelator_32_Supplier_4]
    5448 -> Trasnformador_06 [SpatialRelator_22_Supplier_5]
    5449 -> Trasnformador_06 [SpatialRelator_33_Supplier_4]
    5450 -> Trasnformador_06 [SpatialRelator_34_Supplier_4]
    5451 -> Trasnformador_06 [SpatialRelator_35_Supplier_3]
    5452 -> Trasnformador_06 [SpatialRelator_36_Supplier_2]
    5453 -> Trasnformador_06 [SpatialRelator_37_Supplier_2]
    5454 -> Trasnformador_06 [SpatialRelator_38_Supplier_2]
    5455 -> Trasnformador_06 [SpatialRelator_39_Supplier_2]
    5456 -> Trasnformador_06 [SpatialRelator_40_Supplier_2]
    5457 -> Trasnformador_06 [SpatialRelator_41_Supplier_2]
    5458 -> Trasnformador_06 [SpatialRelator_42_Supplier_2]
    5459 -> Trasnformador_06 [SpatialRelator_43_Supplier_2]
    5460 -> Trasnformador_06 [SpatialRelator_44_Supplier_2]
    5461 -> Trasnformador_06 [SpatialRelator_45_Supplier_2]
    5462 -> Trasnformador_06 [SpatialRelator_46_Supplier_2]
    5463 -> Trasnformador_06 [SpatialRelator_47_Supplier_2]
    5464 -> Trasnformador_06 [SpatialRelator_48_Supplier_2]
    5545 -> Trasnformador_06 [SpatialRelator_49_Supplier_2]
    5546 -> Trasnformador_06 [SpatialRelator_50_Supplier_2]
    5547 -> Trasnformador_06 [SpatialRelator_51_Supplier_2]
    5548 -> Trasnformador_06 [SpatialRelator_52_Supplier_2]
    5549 -> Transformador_07 [SpatialRelator_54_Supplier]
    5550 -> Transformador_07 [SpatialRelator_55_Supplier]
    5551 -> Transformador_07 [SpatialRelator_56_Supplier]
    5552 -> Transformador_07 [SpatialRelator_57_Supplier]
    5553 -> Transformador_07 [SpatialRelator_58_Supplier]
    5554 -> Transformador_07 [SpatialRelator_59_Supplier]
    5555 -> Transformador_07 [SpatialRelator_60_Supplier]
    5556 -> Transformador_07 [SpatialRelator_61_Supplier]
    5557 -> Transformador_07 [SpatialRelator_62_Supplier]
    5558 -> Transformador_07 [SpatialRelator_63_Supplier]
    5559 -> Transformador_07 [SpatialRelator_64_Supplier]
    5560 -> Transformador_07 [SpatialRelator_3_Supplier_8]
    5561 -> Transformador_07 [SpatialRelator_65_Supplier]
    5562 -> Transformador_07 [SpatialRelator_66_Supplier]
    5563 -> Transformador_07 [SpatialRelator_67_Supplier]
    5564 -> Transformador_07 [SpatialRelator_68_Supplier]
    5646 -> Transformador_07 [SpatialRelator_69_Supplier]
    5647 -> Transformador_07 [SpatialRelator_70_Supplier]
    5648 -> Transformador_07 [SpatialRelator_71_Supplier]
    5649 -> Transformador_07 [SpatialRelator_72_Supplier]
    5650 -> Transformador_07 [SpatialRelator_73_Supplier]
    5651 -> Transformador_07 [SpatialRelator_74_Supplier]
    5652 -> Transformador_07 [SpatialRelator_75_Supplier]
    5653 -> Transformador_07 [SpatialRelator_76_Supplier]
    5654 -> Transformador_07 [SpatialRelator_77_Supplier]
    5655 -> Transformador_07 [SpatialRelator_78_Supplier]
    5656 -> Transformador_07 [SpatialRelator_79_Supplier]
    5657 -> Transformador_07 [SpatialRelator_80_Supplier]
    5658 -> Transformador_07 [SpatialRelator_81_Supplier]
    5659 -> Transformador_07 [SpatialRelator_82_Supplier]
    5660 -> Transformador_07 [SpatialRelator_83_Supplier]
    5661 -> Transformador_07 [SpatialRelator_84_Supplier]
    5662 -> Transformador_07 [SpatialRelator_85_Supplier]
    5663 -> Transformador_07 [SpatialRelator_86_Supplier]
    5664 -> Transformador_07 [SpatialRelator_87_Supplier]
    5747 -> Transformador_07 [SpatialRelator_88_Supplier]
    5748 -> Transformador_07 [SpatialRelator_89_Supplier]
    5749 -> Transformador_07 [SpatialRelator_90_Supplier]
    5750 -> Transformador_07 [SpatialRelator_91_Supplier]
    5751 -> Transformador_07 [SpatialRelator_92_Supplier]
    5752 -> Transformador_07 [SpatialRelator_93_Supplier]
    5753 -> Transformador_07 [SpatialRelator_53_Supplier]
    5754 -> Transformador_07 [SpatialRelator_94_Supplier]
    5755 -> Transformador_07 [SpatialRelator_95_Supplier]
    5756 -> Transformador_07 [SpatialRelator_96_Supplier]
    5757 -> Transformador_07 [SpatialRelator_97_Supplier]
    5758 -> Transformador_07 [SpatialRelator_98_Supplier]
    5759 -> Transformador_07 [SpatialRelator_99_Supplier]
    5760 -> Transformador_07 [SpatialRelator_100_Supplier]
    5761 -> Transformador_07 [SpatialRelator_101_Supplier]
    5762 -> Transformador_07 [SpatialRelator_102_Supplier]
    5763 -> Transformador_08 [SpatialRelator_104_Supplier]
    5848 -> Transformador_08 [SpatialRelator_105_Supplier]
    5849 -> Transformador_08 [SpatialRelator_106_Supplier]
    5850 -> Transformador_08 [SpatialRelator_107_Supplier]
    5851 -> Transformador_08 [SpatialRelator_108_Supplier]
    5852 -> Transformador_08 [SpatialRelator_109_Supplier]
    5853 -> Transformador_08 [SpatialRelator_110_Supplier]
    5856 -> Transformador_08 [SpatialRelator_111_Supplier]
    5857 -> Transformador_08 [SpatialRelator_112_Supplier]
    5858 -> Transformador_08 [SpatialRelator_113_Supplier]
    5859 -> Transformador_08 [SpatialRelator_114_Supplier]
    5860 -> Transformador_08 [SpatialRelator_115_Supplier]
    5861 -> Transformador_08 [SpatialRelator_116_Supplier]
    5862 -> Transformador_08 [SpatialRelator_117_Supplier]
    5863 -> Transformador_08 [SpatialRelator_118_Supplier]
    5949 -> Transformador_08 [SpatialRelator_119_Supplier]
    5950 -> Transformador_08 [SpatialRelator_120_Supplier]
    5951 -> Transformador_08 [SpatialRelator_124_Supplier]
    5957 -> Transformador_08 [SpatialRelator_125_Supplier]
    5958 -> Transformador_08 [SpatialRelator_126_Supplier]
    5959 -> Transformador_08 [SpatialRelator_127_Supplier]
    5960 -> Transformador_08 [SpatialRelator_128_Supplier]
    5961 -> Transformador_08 [SpatialRelator_129_Supplier]
    5962 -> Transformador_08 [SpatialRelator_130_Supplier]
    6057 -> Transformador_08 [SpatialRelator_131_Supplier]
    6058 -> Transformador_08 [SpatialRelator_132_Supplier]
    6061 -> Transformador_08 [SpatialRelator_133_Supplier]
Note: Leitura di dataset EDIFICACAO
EDIFICACAO.EDIFICACAO (reader ESRISHAPE_1)
    attributes: ID_EDIFICA long, MODA_MDE double, DESVIO_PAD double, MEDIA_MDE double, COTA_MAX_M double, COTA_MIN_M double, MODA_MDT double, DESVIO_P00 double, MEDIA_MDT double, COTA_MAX00 double, COTA_MIN00 double, ID_LOTE_CT long, AREA double, ARTICULACA char(200), _related_c number(200,10)
    -> Testar_numero_de_relacoes
Note: Testar_numero_de_relacoes
Testar_numero_de_relacoes: Tester
    BOOL_OP = OR
    TEST_CLAUSE = TEST @Value(_related_c) = 1
    PASSED -> AttributeFilter
Note: Filtro das articulações
AttributeFilter
    ATTR_NAME = ARTICULACA
    ATTR_VALUES = <Empty>,<Missing>,<Null>,<Unfiltered>,5151,5146,4243,4244,4245,4341,4342,4343,4344,4345,4439,4440,4441,4442,4443,4444,4538,4539,4540,4541,4542,4543,4544,4545,4548,4549,4550,4551,4552,4553,4556,4557,4635,4636,4637,4638,4639,4640,4641,4642,4643,4644,4645,4646,4647,4648,4649,4650,4651,4652,4653,4654,4655,4656,4657,4658,4659,4660,4661,4662,4735,4736,4737,4738,4739,4740,4741,4742,4743,4744,4745,4746,4747,4748,4749,4750,4751,4752,4753,4754,4755,4756,4757,4758,4759,4760,4761,4762,4763,4764,4837,4838,4839,4840,4841,4842,4843,4844,4845,4846,4847,4848,4849,4850,4851,4852,4853,4854,4855,4856,4857,4858,4859,4860,4861,4862,4863,4864,4865,4866,4939,4940,4941,4942,4943,4944,4945,4946,4947,4948,4949,4950,4951,4952,4953,4954,4955,4956,4957,4958,4959,4960,4961,4962,4963,4964,4965,4966,5041,5042,5043,5044,5045,5046,5047,5048,5049,5050,5051,5052,5053,5054,5055,5056,5057,5058,5059,5060,5061,5062,5063,5064,5065,5066,5141,5142,5143,5144,5145,5146,5147,5148,5149,5150,5151,5152,5153,5154,5155,5156,5157,5158,5159,5160,5161,5162,5163,5164,5165,5166,5167,5243,5244,5245,5246,5247,5248,5249,5250,5251,5252,5253,5254,5255,5256,5257,5258,5259,5260,5261,5262,5263,5264,5265,5266,5267,5344,5345,5346,5347,5348,5349,5350,5351,5352,5353,5354,5355,5356,5357,5358,5359,5360,5361,5362,5363,5364,5445,5446,5447,5448,5449,5450,5451,5452,5453,5454,5455,5456,5457,5458,5459,5460,5461,5462,5463,5464,5545,5546,5547,5548,5549,5550,5551,5552,5553,5554,5555,5556,5557,5558,5559,5560,5561,5562,5563,5564,5646,5647,5648,5649,5650,5651,5652,5653,5654,5655,5656,5657,5658,5659,5660,5661,5662,5663,5664,5747,5748,5749,5750,5751,5752,5753,5754,5755,5756,5757,5758,5759,5760,5761,5762,5763,5848,5849,5850,5851,5852,5853,5856,5857,5858,5859,5860,5861,5862,5863,5949,5950,5951,5957,5958,5959,5960,5961,5962,6057,6058,6061
    5151 -> Transformador_01 [SpatialRelator_Requestor]
    5151 -> Transformador_05 [SpatialRelator_16_Requestor_5]
    5146 -> Transformador_01 [SpatialRelator_2_Requestor]
    5146 -> Transformador_05 [SpatialRelator_11_Requestor_6]
    4243 -> Transformador_01 [SpatialRelator_3_Requestor]
    4244 -> Transformador_01 [SpatialRelator_4_Requestor]
    4245 -> Transformador_01 [SpatialRelator_5_Requestor]
    4341 -> Transformador_01 [SpatialRelator_6_Requestor]
    4342 -> Transformador_01 [SpatialRelator_7_Requestor]
    4343 -> Transformador_01 [SpatialRelator_8_Requestor]
    4344 -> Transformador_01 [SpatialRelator_9_Requestor]
    4345 -> Transformador_01 [SpatialRelator_10_Requestor]
    4439 -> Transformador_01 [SpatialRelator_11_Requestor]
    4440 -> Transformador_01 [SpatialRelator_12_Requestor]
    4441 -> Transformador_01 [SpatialRelator_13_Requestor]
    4442 -> Transformador_01 [SpatialRelator_14_Requestor]
    4443 -> Transformador_02 [SpatialRelator_7_Requestor_1]
    4444 -> Transformador_02 [SpatialRelator_2_Requestor_1]
    4538 -> Transformador_02 [SpatialRelator_3_Requestor_1]
    4539 -> Transformador_02 [SpatialRelator_4_Requestor_1]
    4540 -> Transformador_02 [SpatialRelator_5_Requestor_1]
    4541 -> Transformador_02 [SpatialRelator_6_Requestor_1]
    4542 -> Transformador_02 [SpatialRelator_9_Requestor_1]
    4543 -> Transformador_02 [SpatialRelator_10_Requestor_1]
    4544 -> Transformador_02 [SpatialRelator_11_Requestor_1]
    4545 -> Transformador_02 [SpatialRelator_12_Requestor_1]
    4548 -> Transformador_02 [SpatialRelator_13_Requestor_1]
    4549 -> Transformador_02 [SpatialRelator_14_Requestor_1]
    4550 -> Transformador_02 [SpatialRelator_15_Requestor]
    4551 -> Transformador_02 [SpatialRelator_16_Requestor]
    4552 -> Transformador_02 [SpatialRelator_17_Requestor]
    4553 -> Transformador_02 [SpatialRelator_18_Requestor]
    4556 -> Transformador_02 [SpatialRelator_19_Requestor]
    4557 -> Transformador_02 [SpatialRelator_20_Requestor]
    4635 -> Transformador_02 [SpatialRelator_21_Requestor]
    4636 -> Transformador_03 [SpatialRelator_8_Requestor_1]
    4637 -> Transformador_03 [SpatialRelator_3_Requestor_2]
    4638 -> Transformador_03 [SpatialRelator_4_Requestor_2]
    4639 -> Transformador_03 [SpatialRelator_5_Requestor_2]
    4640 -> Transformador_03 [SpatialRelator_6_Requestor_2]
    4641 -> Transformador_03 [SpatialRelator_7_Requestor_2]
    4642 -> Transformador_03 [SpatialRelator_9_Requestor_2]
    4643 -> Transformador_03 [SpatialRelator_10_Requestor_2]
    4644 -> Transformador_03 [SpatialRelator_11_Requestor_2]
    4645 -> Transformador_03 [SpatialRelator_12_Requestor_2]
    4646 -> Transformador_03 [SpatialRelator_13_Requestor_2]
    4647 -> Transformador_03 [SpatialRelator_25_Requestor]
    4648 -> Transformador_03 [SpatialRelator_14_Requestor_2]
    4649 -> Transformador_03 [SpatialRelator_15_Requestor_1]
    4650 -> Transformador_03 [SpatialRelator_16_Requestor_1]
    4651 -> Transformador_03 [SpatialRelator_17_Requestor_1]
    4652 -> Transformador_03 [SpatialRelator_18_Requestor_1]
    4653 -> Transformador_03 [SpatialRelator_24_Requestor]
    4654 -> Transformador_03 [SpatialRelator_19_Requestor_1]
    4655 -> Transformador_03 [SpatialRelator_20_Requestor_1]
    4656 -> Transformador_03 [SpatialRelator_21_Requestor_1]
    4657 -> Transformador_03 [SpatialRelator_22_Requestor]
    4658 -> Transformador_03 [SpatialRelator_23_Requestor]
    4659 -> Transformador_03 [SpatialRelator_26_Requestor]
    4660 -> Transformador_2 [SpatialRelator_11_Requestor_3]
    4661 -> Transformador_2 [SpatialRelator_3_Requestor_3]
    4662 -> Transformador_2 [SpatialRelator_4_Requestor_3]
    4735 -> Transformador_2 [SpatialRelator_5_Requestor_3]
    4736 -> Transformador_2 [SpatialRelator_9_Requestor_3]
    4737 -> Transformador_2 [SpatialRelator_6_Requestor_3]
    4738 -> Transformador_2 [SpatialRelator_7_Requestor_3]
    4739 -> Transformador_2 [SpatialRelator_8_Requestor_2]
    4740 -> Transformador_2 [SpatialRelator_14_Requestor_3]
    4741 -> Transformador_2 [SpatialRelator_10_Requestor_3]
    4742 -> Transformador_2 [SpatialRelator_12_Requestor_3]
    4743 -> Transformador_2 [SpatialRelator_13_Requestor_3]
    4744 -> Transformador_2 [SpatialRelator_18_Requestor_2]
    4745 -> Transformador_2 [SpatialRelator_15_Requestor_2]
    4746 -> Transformador_2 [SpatialRelator_16_Requestor_2]
    4747 -> Transformador_2 [SpatialRelator_17_Requestor_2]
    4748 -> Transformador_2 [SpatialRelator_22_Requestor_1]
    4749 -> Transformador_2 [SpatialRelator_19_Requestor_2]
    4750 -> Transformador_2 [SpatialRelator_20_Requestor_2]
    4751 -> Transformador_2 [SpatialRelator_21_Requestor_2]
    4752 -> Transformador_2 [SpatialRelator_23_Requestor_1]
    4753 -> Transformador_2 [SpatialRelator_24_Requestor_1]
    4754 -> Transformador_2 [SpatialRelator_26_Requestor_1]
    4755 -> Transformador_2 [SpatialRelator_25_Requestor_1]
    4756 -> Transformador_2 [SpatialRelator_27_Requestor]
    4757 -> Transformador_2 [SpatialRelator_28_Requestor]
    4758 -> Transformador_2 [SpatialRelator_30_Requestor]
    4758 -> Transformador_05 [SpatialRelator_52_Supplier_1]
    4759 -> Transformador_2 [SpatialRelator_29_Requestor]
    4760 -> Transformador_2 [SpatialRelator_31_Requestor]
    4761 -> Transformador_2 [SpatialRelator_32_Requestor]
    4762 -> Transformador_2 [SpatialRelator_34_Requestor]
    4763 -> Transformador_3 [SpatialRelator_28_Requestor_1]
    4764 -> Transformador_3 [SpatialRelator_29_Requestor_1]
    4837 -> Transformador_3 [SpatialRelator_30_Requestor_1]
    4838 -> Transformador_3 [SpatialRelator_3_Requestor_4]
    4839 -> Transformador_3 [SpatialRelator_4_Requestor_4]
    4840 -> Transformador_3 [SpatialRelator_5_Requestor_4]
    4841 -> Transformador_3 [SpatialRelator_6_Requestor_4]
    4842 -> Transformador_3 [SpatialRelator_7_Requestor_4]
    4843 -> Transformador_3 [SpatialRelator_8_Requestor_3]
    4844 -> Transformador_3 [SpatialRelator_9_Requestor_4]
    4845 -> Transformador_3 [SpatialRelator_10_Requestor_4]
    4846 -> Transformador_3 [SpatialRelator_11_Requestor_4]
    4847 -> Transformador_3 [SpatialRelator_12_Requestor_4]
    4848 -> Transformador_3 [SpatialRelator_13_Requestor_4]
    4849 -> Transformador_3 [SpatialRelator_14_Requestor_4]
    4850 -> Transformador_3 [SpatialRelator_15_Requestor_3]
    4851 -> Transformador_3 [SpatialRelator_16_Requestor_3]
    4852 -> Transformador_3 [SpatialRelator_17_Requestor_3]
    4853 -> Transformador_3 [SpatialRelator_18_Requestor_3]
    4854 -> Transformador_3 [SpatialRelator_19_Requestor_3]
    4855 -> Transformador_3 [SpatialRelator_20_Requestor_3]
    4856 -> Transformador_3 [SpatialRelator_21_Requestor_3]
    4857 -> Transformador_3 [SpatialRelator_22_Requestor_2]
    4858 -> Transformador_3 [SpatialRelator_32_Requestor_1]
    4859 -> Transformador_3 [SpatialRelator_34_Requestor_1]
    4860 -> Transformador_3 [SpatialRelator_23_Requestor_2]
    4861 -> Transformador_3 [SpatialRelator_24_Requestor_2]
    4862 -> Transformador_3 [SpatialRelator_25_Requestor_2]
    4863 -> Transformador_3 [SpatialRelator_26_Requestor_2]
    4864 -> Transformador_3 [SpatialRelator_27_Requestor_1]
    4865 -> Transformador_3 [SpatialRelator_31_Requestor_1]
    4866 -> Transformador_3 [SpatialRelator_33_Requestor_1]
    4939 -> Transformador_3 [SpatialRelator_35_Requestor]
    4940 -> Transformador_4 [SpatialRelator_3_Requestor_5]
    4941 -> Transformador_4 [SpatialRelator_4_Requestor_5]
    4942 -> Transformador_4 [SpatialRelator_5_Requestor_5]
    4943 -> Transformador_4 [SpatialRelator_6_Requestor_5]
    4944 -> Transformador_4 [SpatialRelator_7_Requestor_5]
    4945 -> Transformador_4 [SpatialRelator_8_Requestor_4]
    4946 -> Transformador_4 [SpatialRelator_9_Requestor_5]
    4947 -> Transformador_4 [SpatialRelator_10_Requestor_5]
    4948 -> Transformador_4 [SpatialRelator_11_Requestor_5]
    4949 -> Transformador_4 [SpatialRelator_12_Requestor_5]
    4950 -> Transformador_4 [SpatialRelator_13_Requestor_5]
    4951 -> Transformador_4 [SpatialRelator_14_Requestor_5]
    4952 -> Transformador_4 [SpatialRelator_15_Requestor_4]
    4953 -> Transformador_4 [SpatialRelator_16_Requestor_4]
    4954 -> Transformador_4 [SpatialRelator_17_Requestor_4]
    4955 -> Transformador_4 [SpatialRelator_18_Requestor_4]
    4956 -> Transformador_4 [SpatialRelator_19_Requestor_4]
    4957 -> Transformador_4 [SpatialRelator_20_Requestor_4]
    4958 -> Transformador_4 [SpatialRelator_22_Requestor_3]
    4959 -> Transformador_4 [SpatialRelator_21_Requestor_4]
    4960 -> Transformador_4 [SpatialRelator_23_Requestor_3]
    4961 -> Transformador_4 [SpatialRelator_24_Requestor_3]
    4962 -> Transformador_4 [SpatialRelator_25_Requestor_3]
    4963 -> Transformador_4 [SpatialRelator_26_Requestor_3]
    4964 -> Transformador_4 [SpatialRelator_27_Requestor_2]
    4965 -> Transformador_4 [SpatialRelator_29_Requestor_2]
    4966 -> Transformador_4 [SpatialRelator_28_Requestor_2]
    5041 -> Transformador_4 [SpatialRelator_44_Requestor]
    5042 -> Transformador_4 [SpatialRelator_46_Requestor]
    5043 -> Transformador_4 [SpatialRelator_45_Requestor]
    5044 -> Transformador_4 [SpatialRelator_30_Requestor_2]
    5045 -> Transformador_4 [SpatialRelator_31_Requestor_2]
    5046 -> Transformador_4 [SpatialRelator_32_Requestor_2]
    5047 -> Transformador_4 [SpatialRelator_33_Requestor_2]
    5048 -> Transformador_4 [SpatialRelator_34_Requestor_2]
    5049 -> Transformador_4 [SpatialRelator_36_Requestor]
    5050 -> Transformador_4 [SpatialRelator_35_Requestor_1]
    5051 -> Transformador_4 [SpatialRelator_47_Requestor]
    5052 -> Transformador_4 [SpatialRelator_49_Requestor]
    5053 -> Transformador_4 [SpatialRelator_48_Requestor]
    5054 -> Transformador_4 [SpatialRelator_37_Requestor]
    5055 -> Transformador_4 [SpatialRelator_38_Requestor]
    5056 -> Transformador_4 [SpatialRelator_39_Requestor]
    5057 -> Transformador_4 [SpatialRelator_40_Requestor]
    5058 -> Transformador_4 [SpatialRelator_41_Requestor]
    5059 -> Transformador_4 [SpatialRelator_43_Requestor]
    5060 -> Transformador_4 [SpatialRelator_42_Requestor]
    5061 -> Transformador_4 [SpatialRelator_50_Requestor]
    5062 -> Transformador_4 [SpatialRelator_52_Requestor]
    5063 -> Transformador_4 [SpatialRelator_51_Requestor]
    5064 -> Transformador_05 [SpatialRelator_3_Requestor_6]
    5065 -> Transformador_05 [SpatialRelator_4_Requestor_6]
    5066 -> Transformador_05 [SpatialRelator_5_Requestor_6]
    5141 -> Transformador_05 [SpatialRelator_6_Requestor_6]
    5142 -> Transformador_05 [SpatialRelator_7_Requestor_6]
    5143 -> Transformador_05 [SpatialRelator_8_Requestor_5]
    5144 -> Transformador_05 [SpatialRelator_9_Requestor_6]
    5145 -> Transformador_05 [SpatialRelator_10_Requestor_6]
    5147 -> Transformador_05 [SpatialRelator_12_Requestor_6]
    5148 -> Transformador_05 [SpatialRelator_13_Requestor_6]
    5149 -> Transformador_05 [SpatialRelator_14_Requestor_6]
    5150 -> Transformador_05 [SpatialRelator_15_Requestor_5]
    5152 -> Transformador_05 [SpatialRelator_17_Requestor_5]
    5153 -> Transformador_05 [SpatialRelator_18_Requestor_5]
    5154 -> Transformador_05 [SpatialRelator_19_Requestor_5]
    5155 -> Transformador_05 [SpatialRelator_20_Requestor_5]
    5156 -> Transformador_05 [SpatialRelator_21_Requestor_5]
    5157 -> Transformador_05 [SpatialRelator_22_Requestor_4]
    5158 -> Transformador_05 [SpatialRelator_23_Requestor_4]
    5159 -> Transformador_05 [SpatialRelator_24_Requestor_4]
    5160 -> Transformador_05 [SpatialRelator_25_Requestor_4]
    5161 -> Transformador_05 [SpatialRelator_26_Requestor_4]
    5162 -> Transformador_05 [SpatialRelator_27_Requestor_3]
    5163 -> Transformador_05 [SpatialRelator_28_Requestor_3]
    5164 -> Transformador_05 [SpatialRelator_29_Requestor_3]
    5165 -> Transformador_05 [SpatialRelator_30_Requestor_3]
    5166 -> Transformador_05 [SpatialRelator_31_Requestor_3]
    5167 -> Transformador_05 [SpatialRelator_32_Requestor_3]
    5243 -> Transformador_05 [SpatialRelator_33_Requestor_3]
    5244 -> Transformador_05 [SpatialRelator_34_Requestor_3]
    5245 -> Transformador_05 [SpatialRelator_35_Requestor_2]
    5246 -> Transformador_05 [SpatialRelator_36_Requestor_1]
    5247 -> Transformador_05 [SpatialRelator_37_Requestor_1]
    5248 -> Transformador_05 [SpatialRelator_38_Requestor_1]
    5249 -> Transformador_05 [SpatialRelator_39_Requestor_1]
    5250 -> Transformador_05 [SpatialRelator_40_Requestor_1]
    5251 -> Transformador_05 [SpatialRelator_41_Requestor_1]
    5252 -> Transformador_05 [SpatialRelator_42_Requestor_1]
    5253 -> Transformador_05 [SpatialRelator_43_Requestor_1]
    5254 -> Transformador_05 [SpatialRelator_44_Requestor_1]
    5255 -> Transformador_05 [SpatialRelator_45_Requestor_1]
    5256 -> Transformador_05 [SpatialRelator_46_Requestor_1]
    5257 -> Transformador_05 [SpatialRelator_47_Requestor_1]
    5258 -> Transformador_05 [SpatialRelator_48_Requestor_1]
    5259 -> Transformador_05 [SpatialRelator_49_Requestor_1]
    5260 -> Transformador_05 [SpatialRelator_50_Requestor_1]
    5261 -> Transformador_05 [SpatialRelator_51_Requestor_1]
    5262 -> Transformador_05 [SpatialRelator_52_Requestor_1]
    5263 -> Trasnformador_06 [SpatialRelator_3_Requestor_7]
    5264 -> Trasnformador_06 [SpatialRelator_4_Requestor_7]
    5265 -> Trasnformador_06 [SpatialRelator_5_Requestor_7]
    5266 -> Trasnformador_06 [SpatialRelator_6_Requestor_7]
    5267 -> Trasnformador_06 [SpatialRelator_7_Requestor_7]
    5344 -> Trasnformador_06 [SpatialRelator_8_Requestor_6]
    5345 -> Trasnformador_06 [SpatialRelator_9_Requestor_7]
    5346 -> Trasnformador_06 [SpatialRelator_10_Requestor_7]
    5347 -> Trasnformador_06 [SpatialRelator_11_Requestor_7]
    5348 -> Trasnformador_06 [SpatialRelator_12_Requestor_7]
    5349 -> Trasnformador_06 [SpatialRelator_13_Requestor_7]
    5350 -> Trasnformador_06 [SpatialRelator_14_Requestor_7]
    5351 -> Trasnformador_06 [SpatialRelator_15_Requestor_6]
    5352 -> Trasnformador_06 [SpatialRelator_16_Requestor_6]
    5353 -> Trasnformador_06 [SpatialRelator_17_Requestor_6]
    5354 -> Trasnformador_06 [SpatialRelator_18_Requestor_6]
    5355 -> Trasnformador_06 [SpatialRelator_19_Requestor_6]
    5356 -> Trasnformador_06 [SpatialRelator_20_Requestor_6]
    5357 -> Trasnformador_06 [SpatialRelator_21_Requestor_6]
    5358 -> Trasnformador_06 [SpatialRelator_23_Requestor_5]
    5359 -> Trasnformador_06 [SpatialRelator_24_Requestor_5]
    5360 -> Trasnformador_06 [SpatialRelator_25_Requestor_5]
    5361 -> Trasnformador_06 [SpatialRelator_26_Requestor_5]
    5362 -> Trasnformador_06 [SpatialRelator_27_Requestor_4]
    5363 -> Trasnformador_06 [SpatialRelator_28_Requestor_4]
    5364 -> Trasnformador_06 [SpatialRelator_29_Requestor_4]
    5445 -> Trasnformador_06 [SpatialRelator_30_Requestor_4]
    5446 -> Trasnformador_06 [SpatialRelator_31_Requestor_4]
    5447 -> Trasnformador_06 [SpatialRelator_32_Requestor_4]
    5448 -> Trasnformador_06 [SpatialRelator_22_Requestor_5]
    5449 -> Trasnformador_06 [SpatialRelator_33_Requestor_4]
    5450 -> Trasnformador_06 [SpatialRelator_34_Requestor_4]
    5451 -> Trasnformador_06 [SpatialRelator_35_Requestor_3]
    5452 -> Trasnformador_06 [SpatialRelator_36_Requestor_2]
    5453 -> Trasnformador_06 [SpatialRelator_37_Requestor_2]
    5454 -> Trasnformador_06 [SpatialRelator_38_Requestor_2]
    5455 -> Trasnformador_06 [SpatialRelator_39_Requestor_2]
    5456 -> Trasnformador_06 [SpatialRelator_40_Requestor_2]
    5457 -> Trasnformador_06 [SpatialRelator_41_Requestor_2]
    5458 -> Trasnformador_06 [SpatialRelator_42_Requestor_2]
    5459 -> Trasnformador_06 [SpatialRelator_43_Requestor_2]
    5460 -> Trasnformador_06 [SpatialRelator_44_Requestor_2]
    5461 -> Trasnformador_06 [SpatialRelator_45_Requestor_2]
    5462 -> Trasnformador_06 [SpatialRelator_46_Requestor_2]
    5463 -> Trasnformador_06 [SpatialRelator_47_Requestor_2]
    5464 -> Trasnformador_06 [SpatialRelator_48_Requestor_2]
    5545 -> Trasnformador_06 [SpatialRelator_49_Requestor_2]
    5546 -> Trasnformador_06 [SpatialRelator_50_Requestor_2]
    5547 -> Trasnformador_06 [SpatialRelator_51_Requestor_2]
    5548 -> Trasnformador_06 [SpatialRelator_52_Requestor_2]
    5549 -> Transformador_07 [SpatialRelator_54_Requestor]
    5550 -> Transformador_07 [SpatialRelator_55_Requestor]
    5551 -> Transformador_07 [SpatialRelator_56_Requestor]
    5552 -> Transformador_07 [SpatialRelator_57_Requestor]
    5553 -> Transformador_07 [SpatialRelator_58_Requestor]
    5554 -> Transformador_07 [SpatialRelator_59_Requestor]
    5555 -> Transformador_07 [SpatialRelator_60_Requestor]
    5556 -> Transformador_07 [SpatialRelator_61_Requestor]
    5557 -> Transformador_07 [SpatialRelator_62_Requestor]
    5558 -> Transformador_07 [SpatialRelator_63_Requestor]
    5559 -> Transformador_07 [SpatialRelator_64_Requestor]
    5560 -> Transformador_07 [SpatialRelator_3_Requestor_8]
    5561 -> Transformador_07 [SpatialRelator_65_Requestor]
    5562 -> Transformador_07 [SpatialRelator_66_Requestor]
    5563 -> Transformador_07 [SpatialRelator_67_Requestor]
    5564 -> Transformador_07 [SpatialRelator_68_Requestor]
    5646 -> Transformador_07 [SpatialRelator_69_Requestor]
    5647 -> Transformador_07 [SpatialRelator_70_Requestor]
    5648 -> Transformador_07 [SpatialRelator_71_Requestor]
    5649 -> Transformador_07 [SpatialRelator_72_Requestor]
    5650 -> Transformador_07 [SpatialRelator_73_Requestor]
    5651 -> Transformador_07 [SpatialRelator_74_Requestor]
    5652 -> Transformador_07 [SpatialRelator_75_Requestor]
    5653 -> Transformador_07 [SpatialRelator_76_Requestor]
    5654 -> Transformador_07 [SpatialRelator_77_Requestor]
    5655 -> Transformador_07 [SpatialRelator_78_Requestor]
    5656 -> Transformador_07 [SpatialRelator_79_Requestor]
    5657 -> Transformador_07 [SpatialRelator_80_Requestor]
    5658 -> Transformador_07 [SpatialRelator_81_Requestor]
    5659 -> Transformador_07 [SpatialRelator_82_Requestor]
    5660 -> Transformador_07 [SpatialRelator_83_Requestor]
    5661 -> Transformador_07 [SpatialRelator_84_Requestor]
    5662 -> Transformador_07 [SpatialRelator_85_Requestor]
    5663 -> Transformador_07 [SpatialRelator_86_Requestor]
    5664 -> Transformador_07 [SpatialRelator_87_Requestor]
    5747 -> Transformador_07 [SpatialRelator_88_Requestor]
    5748 -> Transformador_07 [SpatialRelator_89_Requestor]
    5749 -> Transformador_07 [SpatialRelator_90_Requestor]
    5750 -> Transformador_07 [SpatialRelator_91_Requestor]
    5751 -> Transformador_07 [SpatialRelator_92_Requestor]
    5752 -> Transformador_07 [SpatialRelator_93_Requestor]
    5753 -> Transformador_07 [SpatialRelator_53_Requestor]
    5754 -> Transformador_07 [SpatialRelator_94_Requestor]
    5755 -> Transformador_07 [SpatialRelator_95_Requestor]
    5756 -> Transformador_07 [SpatialRelator_96_Requestor]
    5757 -> Transformador_07 [SpatialRelator_97_Requestor]
    5758 -> Transformador_07 [SpatialRelator_98_Requestor]
    5759 -> Transformador_07 [SpatialRelator_99_Requestor]
    5760 -> Transformador_07 [SpatialRelator_100_Requestor]
    5761 -> Transformador_07 [SpatialRelator_101_Requestor]
    5762 -> Transformador_07 [SpatialRelator_102_Requestor]
    5763 -> Transformador_08 [SpatialRelator_104_Requestor]
    5848 -> Transformador_08 [SpatialRelator_105_Requestor]
    5849 -> Transformador_08 [SpatialRelator_106_Requestor]
    5850 -> Transformador_08 [SpatialRelator_107_Requestor]
    5851 -> Transformador_08 [SpatialRelator_108_Requestor]
    5852 -> Transformador_08 [SpatialRelator_109_Requestor]
    5853 -> Transformador_08 [SpatialRelator_110_Requestor]
    5856 -> Transformador_08 [SpatialRelator_111_Requestor]
    5857 -> Transformador_08 [SpatialRelator_112_Requestor]
    5858 -> Transformador_08 [SpatialRelator_113_Requestor]
    5859 -> Transformador_08 [SpatialRelator_114_Requestor]
    5860 -> Transformador_08 [SpatialRelator_115_Requestor]
    5861 -> Transformador_08 [SpatialRelator_116_Requestor]
    5862 -> Transformador_08 [SpatialRelator_117_Requestor]
    5863 -> Transformador_08 [SpatialRelator_118_Requestor]
    5949 -> Transformador_08 [SpatialRelator_119_Requestor]
    5950 -> Transformador_08 [SpatialRelator_120_Requestor]
    5951 -> Transformador_08 [SpatialRelator_124_Requestor]
    5957 -> Transformador_08 [SpatialRelator_125_Requestor]
    5958 -> Transformador_08 [SpatialRelator_126_Requestor]
    5959 -> Transformador_08 [SpatialRelator_127_Requestor]
    5960 -> Transformador_08 [SpatialRelator_128_Requestor]
    5961 -> Transformador_08 [SpatialRelator_129_Requestor]
    5962 -> Transformador_08 [SpatialRelator_130_Requestor]
    6057 -> Transformador_08 [SpatialRelator_131_Requestor]
    6058 -> Transformador_08 [SpatialRelator_132_Requestor]
    6061 -> Transformador_08 [SpatialRelator_133_Requestor]
Transformador_01
    LIST_ATTRS_TO_INCLUDE = _indices{}.z
    SpatialRelator_Output -> PythonCaller
Transformador_2
    LIST_ATTRS_TO_INCLUDE = _indices{}.z
    -> PythonCaller
Transformador_02
    LIST_ATTRS_TO_INCLUDE = _indices{}.z
    SpatialRelator_Output -> PythonCaller
Transformador_03
    LIST_ATTRS_TO_INCLUDE = _indices{}.z
    -> PythonCaller
Transformador_05
    LIST_ATTRS_TO_INCLUDE = _indices{}.z
    -> PythonCaller
Transformador_3
    LIST_ATTRS_TO_INCLUDE = _indices{}.z
    -> PythonCaller
Transformador_4
    LIST_ATTRS_TO_INCLUDE = _indices{}.z
    -> PythonCaller
Trasnformador_06
    LIST_ATTRS_TO_INCLUDE = _indices{}.z
    -> PythonCaller
Transformador_07
    LIST_ATTRS_TO_INCLUDE = _indices{}.z
    -> PythonCaller
Transformador_08
    LIST_ATTRS_TO_INCLUDE = _indices{}.z
    -> PythonCaller
Note: Realiza do calculo da media e moda do mds desvio padrao, maximo e minimo valor
PythonCaller
    PYTHONSOURCE:
      import fme
      import fmeobjects
      # Template Function interface:
      # When using this function, make sure its name is set as the value of
      # the 'Class or Function to Process Features' transformer parameter
      def processFeature(feature):
          pass

      # Tranformador para gerar as estatisticas
      class FeatureProcessor(object):
          def __init__(self):
              pass
          def input(self,feature):
              #percorrer o _indices e buscar todos os valores do indice Z
              i = 0
              dados = list()
              while True:
                  v = feature.getAttribute('_indices{%d}.z' % i)
                  dados.append(number)
                  if v == None:
                      break
                  i += 1
              feature.setAttribute("MODA_MDS", (dados))  #setar o valor da moda_mds
              feature.setAttribute("MEDIA_MDS", media(dados))  #setar o valor da MEDIA
              feature.setAttribute("DESVIO_PADRAO_MDS", desvio_padrao(dados))  #setar o valor da DESVIO_PADRAO_MDS
              feature.setAttribute("COTA_MAX_MDS", max(dados))  #setar o valor da DESVIO_PADRAO_MDS
              feature.setAttribute("COTA_MIN_MDS", min(dados))  #setar o valor da DESVIO_PADRAO_MDS
              self.pyoutput(feature)
          def close(self):
              pass

          # calculo da media
          def media(dados):
              dados.sort() #.sort
              if len(dados) % 2 == 0:
                  n = len(dados)
                  media = (dados[n / 2 - 1] + dados[n / 2]) / 2
              else:
                  media = datos[len(dados) / 2]

              return media

          # calculo da moda
          def moda(dados):
              repeticiones = 0

              for i in dados:
                  n = dados.count(i)
                  ifn > repeticiones:
                      repeticiones = n
              moda = []
              for i in dados:
                  n = dados.count(i) #
                  ifn == repeticiones and i notin dados:
                      dados.append(i)

              if len(moda) != len(datos):
                  return moda
              else:
                  return moda

          # calculo da variancia
          def variancia(dados):
              _media = media(dados)
              soma = 0
              _variancia = 0

              for valor in valores:
                  soma += math.pow( (valor - _media), 2)
              _variancia = soma / float( len(valores) )
              return _variancia

          # calculo do desvio padroa
          def desvio_padrao(dados):
              return math.sqrt( variancia(dados) )
    PYTHONSYMBOL = FeatureProcessor
    -> EDIFICACAO.EDIFICACAO (writer ESRISHAPE_2)
Note: Salvar os dados em um novo dataset
EDIFICACAO.EDIFICACAO (writer ESRISHAPE_2)
    attributes: ID_EDIFICA long, MODA_MDE double, DESVIO_PAD double, MEDIA_MDE double, COTA_MAX_M double, COTA_MIN_M double, MODA_MDT double, DESVIO_P00 double, MEDIA_MDT double, COTA_MAX00 double, COTA_MIN00 double, ID_LOTE_CT long, AREA double, ARTICULACA char(200), _related_c number(200,10)

FME custom transformer Transformador_2

Parameters:
- LIST_ATTRS_TO_INCLUDE = _indices{}.z   # NO_EXPAND_LIST Indices{}.z

SpatialRelator_11_Requestor_3 (input)
    -> SpatialRelator_11 [Requestor]
SpatialRelator_11_Supplier_3 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_9_Requestor_3 (input)
    -> SpatialRelator_9 [Requestor]
SpatialRelator_9_Supplier_3 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_14_Requestor_3 (input)
    -> SpatialRelator_14 [Requestor]
SpatialRelator_14_Supplier_3 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_18_Requestor_2 (input)
    -> SpatialRelator_18 [Requestor]
SpatialRelator_18_Supplier_2 (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_22_Requestor_1 (input)
    -> SpatialRelator_22 [Requestor]
SpatialRelator_22_Supplier_1 (input)
    -> SpatialRelator_22 [Supplier]
SpatialRelator_22
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_23_Requestor_1 (input)
    -> SpatialRelator_23 [Requestor]
SpatialRelator_23_Supplier_1 (input)
    -> SpatialRelator_23 [Supplier]
SpatialRelator_23
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_27_Requestor (input)
    -> SpatialRelator_27 [Requestor]
SpatialRelator_27_Supplier (input)
    -> SpatialRelator_27 [Supplier]
SpatialRelator_27
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_31_Requestor (input)
    -> SpatialRelator_31 [Requestor]
SpatialRelator_31_Supplier (input)
    -> SpatialRelator_31 [Supplier]
SpatialRelator_31
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_3_Requestor_3 (input)
    -> SpatialRelator_3 [Requestor]
SpatialRelator_3_Supplier_3 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_6_Requestor_3 (input)
    -> SpatialRelator_6 [Requestor]
SpatialRelator_6_Supplier_3 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_10_Requestor_3 (input)
    -> SpatialRelator_10 [Requestor]
SpatialRelator_10_Supplier_3 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_15_Requestor_2 (input)
    -> SpatialRelator_15 [Requestor]
SpatialRelator_15_Supplier_2 (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_19_Requestor_2 (input)
    -> SpatialRelator_19 [Requestor]
SpatialRelator_19_Supplier_2 (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_24_Requestor_1 (input)
    -> SpatialRelator_24 [Requestor]
SpatialRelator_24_Supplier_1 (input)
    -> SpatialRelator_24 [Supplier]
SpatialRelator_24
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_28_Requestor (input)
    -> SpatialRelator_28 [Requestor]
SpatialRelator_28_Supplier (input)
    -> SpatialRelator_28 [Supplier]
SpatialRelator_28
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_32_Requestor (input)
    -> SpatialRelator_32 [Requestor]
SpatialRelator_32_Supplier (input)
    -> SpatialRelator_32 [Supplier]
SpatialRelator_32
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_4_Requestor_3 (input)
    -> SpatialRelator_4 [Requestor]
SpatialRelator_4_Supplier_3 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_7_Requestor_3 (input)
    -> SpatialRelator_7 [Requestor]
SpatialRelator_7_Supplier_3 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_12_Requestor_3 (input)
    -> SpatialRelator_12 [Requestor]
SpatialRelator_12_Supplier_3 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_16_Requestor_2 (input)
    -> SpatialRelator_16 [Requestor]
SpatialRelator_16_Supplier_2 (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_20_Requestor_2 (input)
    -> SpatialRelator_20 [Requestor]
SpatialRelator_20_Supplier_2 (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_26_Requestor_1 (input)
    -> SpatialRelator_26 [Requestor]
SpatialRelator_26_Supplier_1 (input)
    -> SpatialRelator_26 [Supplier]
SpatialRelator_26
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_30_Requestor (input)
    -> SpatialRelator_30 [Requestor]
SpatialRelator_30_Supplier (input)
    -> SpatialRelator_30 [Supplier]
SpatialRelator_30
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_34_Requestor (input)
    -> SpatialRelator_34 [Requestor]
SpatialRelator_34_Supplier (input)
    -> SpatialRelator_34 [Supplier]
SpatialRelator_34
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_5_Requestor_3 (input)
    -> SpatialRelator_5 [Requestor]
SpatialRelator_5_Supplier_3 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_8_Requestor_2 (input)
    -> SpatialRelator_8 [Requestor]
SpatialRelator_8_Supplier_2 (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_13_Requestor_3 (input)
    -> SpatialRelator_13 [Requestor]
SpatialRelator_13_Supplier_3 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_17_Requestor_2 (input)
    -> SpatialRelator_17 [Requestor]
SpatialRelator_17_Supplier_2 (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_21_Requestor_2 (input)
    -> SpatialRelator_21 [Requestor]
SpatialRelator_21_Supplier_2 (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_25_Requestor_1 (input)
    -> SpatialRelator_25 [Requestor]
SpatialRelator_25_Supplier_1 (input)
    -> SpatialRelator_25 [Supplier]
SpatialRelator_25
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_29_Requestor (input)
    -> SpatialRelator_29 [Requestor]
SpatialRelator_29_Supplier (input)
    -> SpatialRelator_29 [Supplier]
SpatialRelator_29
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_33_Requestor (input)
    -> SpatialRelator_33 [Requestor]
SpatialRelator_33_Supplier (input)
    -> SpatialRelator_33 [Supplier]
SpatialRelator_33
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_08

Parameters:
- LIST_ATTRS_TO_INCLUDE = _indices{}.z   # NO_EXPAND_LIST Indices{}.z

SpatialRelator_104_Requestor (input)
    -> SpatialRelator_104 [Requestor]
SpatialRelator_104_Supplier (input)
    -> SpatialRelator_104 [Supplier]
SpatialRelator_104
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_105_Requestor (input)
    -> SpatialRelator_105 [Requestor]
SpatialRelator_105_Supplier (input)
    -> SpatialRelator_105 [Supplier]
SpatialRelator_105
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_106_Requestor (input)
    -> SpatialRelator_106 [Requestor]
SpatialRelator_106_Supplier (input)
    -> SpatialRelator_106 [Supplier]
SpatialRelator_106
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_107_Requestor (input)
    -> SpatialRelator_107 [Requestor]
SpatialRelator_107_Supplier (input)
    -> SpatialRelator_107 [Supplier]
SpatialRelator_107
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_108_Requestor (input)
    -> SpatialRelator_108 [Requestor]
SpatialRelator_108_Supplier (input)
    -> SpatialRelator_108 [Supplier]
SpatialRelator_108
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_109_Requestor (input)
    -> SpatialRelator_109 [Requestor]
SpatialRelator_109_Supplier (input)
    -> SpatialRelator_109 [Supplier]
SpatialRelator_109
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_110_Requestor (input)
    -> SpatialRelator_110 [Requestor]
SpatialRelator_110_Supplier (input)
    -> SpatialRelator_110 [Supplier]
SpatialRelator_110
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_111_Requestor (input)
    -> SpatialRelator_111 [Requestor]
SpatialRelator_111_Supplier (input)
    -> SpatialRelator_111 [Supplier]
SpatialRelator_111
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_112_Requestor (input)
    -> SpatialRelator_112 [Requestor]
SpatialRelator_112_Supplier (input)
    -> SpatialRelator_112 [Supplier]
SpatialRelator_112
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_113_Requestor (input)
    -> SpatialRelator_113 [Requestor]
SpatialRelator_113_Supplier (input)
    -> SpatialRelator_113 [Supplier]
SpatialRelator_113
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_114_Requestor (input)
    -> SpatialRelator_114 [Requestor]
SpatialRelator_114_Supplier (input)
    -> SpatialRelator_114 [Supplier]
SpatialRelator_114
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_115_Requestor (input)
    -> SpatialRelator_115 [Requestor]
SpatialRelator_115_Supplier (input)
    -> SpatialRelator_115 [Supplier]
SpatialRelator_115
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_116_Requestor (input)
    -> SpatialRelator_116 [Requestor]
SpatialRelator_116_Supplier (input)
    -> SpatialRelator_116 [Supplier]
SpatialRelator_116
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_117_Requestor (input)
    -> SpatialRelator_117 [Requestor]
SpatialRelator_117_Supplier (input)
    -> SpatialRelator_117 [Supplier]
SpatialRelator_117
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_118_Requestor (input)
    -> SpatialRelator_118 [Requestor]
SpatialRelator_118_Supplier (input)
    -> SpatialRelator_118 [Supplier]
SpatialRelator_118
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_119_Requestor (input)
    -> SpatialRelator_119 [Requestor]
SpatialRelator_119_Supplier (input)
    -> SpatialRelator_119 [Supplier]
SpatialRelator_119
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_120_Requestor (input)
    -> SpatialRelator_120 [Requestor]
SpatialRelator_120_Supplier (input)
    -> SpatialRelator_120 [Supplier]
SpatialRelator_120
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_124_Requestor (input)
    -> SpatialRelator_124 [Requestor]
SpatialRelator_124_Supplier (input)
    -> SpatialRelator_124 [Supplier]
SpatialRelator_124
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_125_Requestor (input)
    -> SpatialRelator_125 [Requestor]
SpatialRelator_125_Supplier (input)
    -> SpatialRelator_125 [Supplier]
SpatialRelator_125
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_126_Requestor (input)
    -> SpatialRelator_126 [Requestor]
SpatialRelator_126_Supplier (input)
    -> SpatialRelator_126 [Supplier]
SpatialRelator_126
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_127_Requestor (input)
    -> SpatialRelator_127 [Requestor]
SpatialRelator_127_Supplier (input)
    -> SpatialRelator_127 [Supplier]
SpatialRelator_127
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_128_Requestor (input)
    -> SpatialRelator_128 [Requestor]
SpatialRelator_128_Supplier (input)
    -> SpatialRelator_128 [Supplier]
SpatialRelator_128
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_129_Requestor (input)
    -> SpatialRelator_129 [Requestor]
SpatialRelator_129_Supplier (input)
    -> SpatialRelator_129 [Supplier]
SpatialRelator_129
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_130_Requestor (input)
    -> SpatialRelator_130 [Requestor]
SpatialRelator_130_Supplier (input)
    -> SpatialRelator_130 [Supplier]
SpatialRelator_130
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_131_Requestor (input)
    -> SpatialRelator_131 [Requestor]
SpatialRelator_131_Supplier (input)
    -> SpatialRelator_131 [Supplier]
SpatialRelator_131
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_132_Requestor (input)
    -> SpatialRelator_132 [Requestor]
SpatialRelator_132_Supplier (input)
    -> SpatialRelator_132 [Supplier]
SpatialRelator_132
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_133_Requestor (input)
    -> SpatialRelator_133 [Requestor]
SpatialRelator_133_Supplier (input)
    -> SpatialRelator_133 [Supplier]
SpatialRelator_133
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_4

Parameters:
- LIST_ATTRS_TO_INCLUDE = _indices{}.z   # NO_EXPAND_LIST Indices{}.z

SpatialRelator_3_Requestor_5 (input)
    -> SpatialRelator_3 [Requestor]
SpatialRelator_3_Supplier_5 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_4_Requestor_5 (input)
    -> SpatialRelator_4 [Requestor]
SpatialRelator_4_Supplier_5 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_5_Requestor_5 (input)
    -> SpatialRelator_5 [Requestor]
SpatialRelator_5_Supplier_5 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_6_Requestor_5 (input)
    -> SpatialRelator_6 [Requestor]
SpatialRelator_6_Supplier_5 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_7_Requestor_5 (input)
    -> SpatialRelator_7 [Requestor]
SpatialRelator_7_Supplier_5 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_8_Requestor_4 (input)
    -> SpatialRelator_8 [Requestor]
SpatialRelator_8_Supplier_4 (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_9_Requestor_5 (input)
    -> SpatialRelator_9 [Requestor]
SpatialRelator_9_Supplier_5 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_10_Requestor_5 (input)
    -> SpatialRelator_10 [Requestor]
SpatialRelator_10_Supplier_5 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_11_Requestor_5 (input)
    -> SpatialRelator_11 [Requestor]
SpatialRelator_11_Supplier_5 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_12_Requestor_5 (input)
    -> SpatialRelator_12 [Requestor]
SpatialRelator_12_Supplier_5 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_13_Requestor_5 (input)
    -> SpatialRelator_13 [Requestor]
SpatialRelator_13_Supplier_5 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_14_Requestor_5 (input)
    -> SpatialRelator_14 [Requestor]
SpatialRelator_14_Supplier_5 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_15_Requestor_4 (input)
    -> SpatialRelator_15 [Requestor]
SpatialRelator_15_Supplier_4 (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_16_Requestor_4 (input)
    -> SpatialRelator_16 [Requestor]
SpatialRelator_16_Supplier_4 (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_17_Requestor_4 (input)
    -> SpatialRelator_17 [Requestor]
SpatialRelator_17_Supplier_4 (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_18_Requestor_4 (input)
    -> SpatialRelator_18 [Requestor]
SpatialRelator_18_Supplier_4 (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_19_Requestor_4 (input)
    -> SpatialRelator_19 [Requestor]
SpatialRelator_19_Supplier_4 (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_20_Requestor_4 (input)
    -> SpatialRelator_20 [Requestor]
SpatialRelator_20_Supplier_4 (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_22_Requestor_3 (input)
    -> SpatialRelator_22 [Requestor]
SpatialRelator_22_Supplier_3 (input)
    -> SpatialRelator_22 [Supplier]
SpatialRelator_22
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_21_Requestor_4 (input)
    -> SpatialRelator_21 [Requestor]
SpatialRelator_21_Supplier_4 (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_23_Requestor_3 (input)
    -> SpatialRelator_23 [Requestor]
SpatialRelator_23_Supplier_3 (input)
    -> SpatialRelator_23 [Supplier]
SpatialRelator_23
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_24_Requestor_3 (input)
    -> SpatialRelator_24 [Requestor]
SpatialRelator_24_Supplier_3 (input)
    -> SpatialRelator_24 [Supplier]
SpatialRelator_24
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_25_Requestor_3 (input)
    -> SpatialRelator_25 [Requestor]
SpatialRelator_25_Supplier_3 (input)
    -> SpatialRelator_25 [Supplier]
SpatialRelator_25
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_26_Requestor_3 (input)
    -> SpatialRelator_26 [Requestor]
SpatialRelator_26_Supplier_3 (input)
    -> SpatialRelator_26 [Supplier]
SpatialRelator_26
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_27_Requestor_2 (input)
    -> SpatialRelator_27 [Requestor]
SpatialRelator_27_Supplier_2 (input)
    -> SpatialRelator_27 [Supplier]
SpatialRelator_27
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_29_Requestor_2 (input)
    -> SpatialRelator_29 [Requestor]
SpatialRelator_29_Supplier_2 (input)
    -> SpatialRelator_29 [Supplier]
SpatialRelator_29
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_28_Requestor_2 (input)
    -> SpatialRelator_28 [Requestor]
SpatialRelator_28_Supplier_2 (input)
    -> SpatialRelator_28 [Supplier]
SpatialRelator_28
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_44_Requestor (input)
    -> SpatialRelator_44 [Requestor]
SpatialRelator_44_Supplier (input)
    -> SpatialRelator_44 [Supplier]
SpatialRelator_44
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_46_Requestor (input)
    -> SpatialRelator_46 [Requestor]
SpatialRelator_46_Supplier (input)
    -> SpatialRelator_46 [Supplier]
SpatialRelator_46
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_45_Requestor (input)
    -> SpatialRelator_45 [Requestor]
SpatialRelator_45_Supplier (input)
    -> SpatialRelator_45 [Supplier]
SpatialRelator_45
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_30_Requestor_2 (input)
    -> SpatialRelator_30 [Requestor]
SpatialRelator_30_Supplier_2 (input)
    -> SpatialRelator_30 [Supplier]
SpatialRelator_30
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_31_Requestor_2 (input)
    -> SpatialRelator_31 [Requestor]
SpatialRelator_31_Supplier_2 (input)
    -> SpatialRelator_31 [Supplier]
SpatialRelator_31
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_32_Requestor_2 (input)
    -> SpatialRelator_32 [Requestor]
SpatialRelator_32_Supplier_2 (input)
    -> SpatialRelator_32 [Supplier]
SpatialRelator_32
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_33_Requestor_2 (input)
    -> SpatialRelator_33 [Requestor]
SpatialRelator_33_Supplier_2 (input)
    -> SpatialRelator_33 [Supplier]
SpatialRelator_33
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_34_Requestor_2 (input)
    -> SpatialRelator_34 [Requestor]
SpatialRelator_34_Supplier_2 (input)
    -> SpatialRelator_34 [Supplier]
SpatialRelator_34
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_35_Requestor_1 (input)
    -> SpatialRelator_35 [Requestor]
SpatialRelator_35_Supplier_1 (input)
    -> SpatialRelator_35 [Supplier]
SpatialRelator_35
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_36_Requestor (input)
    -> SpatialRelator_36 [Requestor]
SpatialRelator_36_Supplier (input)
    -> SpatialRelator_36 [Supplier]
SpatialRelator_36
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_47_Requestor (input)
    -> SpatialRelator_47 [Requestor]
SpatialRelator_47_Supplier (input)
    -> SpatialRelator_47 [Supplier]
SpatialRelator_47
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_49_Requestor (input)
    -> SpatialRelator_49 [Requestor]
SpatialRelator_49_Supplier (input)
    -> SpatialRelator_49 [Supplier]
SpatialRelator_49
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_48_Requestor (input)
    -> SpatialRelator_48 [Requestor]
SpatialRelator_48_Supplier (input)
    -> SpatialRelator_48 [Supplier]
SpatialRelator_48
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_37_Requestor (input)
    -> SpatialRelator_37 [Requestor]
SpatialRelator_37_Supplier (input)
    -> SpatialRelator_37 [Supplier]
SpatialRelator_37
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_38_Requestor (input)
    -> SpatialRelator_38 [Requestor]
SpatialRelator_38_Supplier (input)
    -> SpatialRelator_38 [Supplier]
SpatialRelator_38
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_39_Requestor (input)
    -> SpatialRelator_39 [Requestor]
SpatialRelator_39_Supplier (input)
    -> SpatialRelator_39 [Supplier]
SpatialRelator_39
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_40_Requestor (input)
    -> SpatialRelator_40 [Requestor]
SpatialRelator_40_Supplier (input)
    -> SpatialRelator_40 [Supplier]
SpatialRelator_40
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_41_Requestor (input)
    -> SpatialRelator_41 [Requestor]
SpatialRelator_41_Supplier (input)
    -> SpatialRelator_41 [Supplier]
SpatialRelator_41
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_43_Requestor (input)
    -> SpatialRelator_43 [Requestor]
SpatialRelator_43_Supplier (input)
    -> SpatialRelator_43 [Supplier]
SpatialRelator_43
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_42_Requestor (input)
    -> SpatialRelator_42 [Requestor]
SpatialRelator_42_Supplier (input)
    -> SpatialRelator_42 [Supplier]
SpatialRelator_42
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_50_Requestor (input)
    -> SpatialRelator_50 [Requestor]
SpatialRelator_50_Supplier (input)
    -> SpatialRelator_50 [Supplier]
SpatialRelator_50
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_52_Requestor (input)
    -> SpatialRelator_52 [Requestor]
SpatialRelator_52_Supplier (input)
    -> SpatialRelator_52 [Supplier]
SpatialRelator_52
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_51_Requestor (input)
    -> SpatialRelator_51 [Requestor]
SpatialRelator_51_Supplier (input)
    -> SpatialRelator_51 [Supplier]
SpatialRelator_51
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_01

Parameters:
- LIST_ATTRS_TO_INCLUDE = _indices{}.z   # NO_EXPAND_LIST Indices{}.z

SpatialRelator_Requestor (input)
    -> SpatialRelator [Requestor]
SpatialRelator_Supplier (input)
    -> SpatialRelator [Supplier]
Note: Calcula a relalção espacial entre o edificaçao e pontos
SpatialRelator
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_2_Requestor (input)
    -> SpatialRelator_2 [Requestor]
SpatialRelator_2_Supplier (input)
    -> SpatialRelator_2 [Supplier]
SpatialRelator_2
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_3_Requestor (input)
    -> SpatialRelator_3 [Requestor]
SpatialRelator_3_Supplier (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_4_Requestor (input)
    -> SpatialRelator_4 [Requestor]
SpatialRelator_4_Supplier (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_5_Requestor (input)
    -> SpatialRelator_5 [Requestor]
SpatialRelator_5_Supplier (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_6_Requestor (input)
    -> SpatialRelator_6 [Requestor]
SpatialRelator_6_Supplier (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_7_Requestor (input)
    -> SpatialRelator_7 [Requestor]
SpatialRelator_7_Supplier (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_8_Requestor (input)
    -> SpatialRelator_8 [Requestor]
SpatialRelator_8_Supplier (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_9_Requestor (input)
    -> SpatialRelator_9 [Requestor]
SpatialRelator_9_Supplier (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_10_Requestor (input)
    -> SpatialRelator_10 [Requestor]
SpatialRelator_10_Supplier (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_11_Requestor (input)
    -> SpatialRelator_11 [Requestor]
SpatialRelator_11_Supplier (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_12_Requestor (input)
    -> SpatialRelator_12 [Requestor]
SpatialRelator_12_Supplier (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_13_Requestor (input)
    -> SpatialRelator_13 [Requestor]
SpatialRelator_13_Supplier (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_14_Requestor (input)
    -> SpatialRelator_14 [Requestor]
SpatialRelator_14_Supplier (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_Output (output)

FME custom transformer Trasnformador_06

Parameters:
- LIST_ATTRS_TO_INCLUDE = _indices{}.z   # NO_EXPAND_LIST Indices{}.z

SpatialRelator_3_Requestor_7 (input)
    -> SpatialRelator_3 [Requestor]
SpatialRelator_3_Supplier_7 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_4_Requestor_7 (input)
    -> SpatialRelator_4 [Requestor]
SpatialRelator_4_Supplier_7 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_5_Requestor_7 (input)
    -> SpatialRelator_5 [Requestor]
SpatialRelator_5_Supplier_7 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_6_Requestor_7 (input)
    -> SpatialRelator_6 [Requestor]
SpatialRelator_6_Supplier_7 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_7_Requestor_7 (input)
    -> SpatialRelator_7 [Requestor]
SpatialRelator_7_Supplier_7 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_8_Requestor_6 (input)
    -> SpatialRelator_8 [Requestor]
SpatialRelator_8_Supplier_6 (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_9_Requestor_7 (input)
    -> SpatialRelator_9 [Requestor]
SpatialRelator_9_Supplier_7 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_10_Requestor_7 (input)
    -> SpatialRelator_10 [Requestor]
SpatialRelator_10_Supplier_7 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_11_Requestor_7 (input)
    -> SpatialRelator_11 [Requestor]
SpatialRelator_11_Supplier_7 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_12_Requestor_7 (input)
    -> SpatialRelator_12 [Requestor]
SpatialRelator_12_Supplier_7 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_13_Requestor_7 (input)
    -> SpatialRelator_13 [Requestor]
SpatialRelator_13_Supplier_7 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_14_Requestor_7 (input)
    -> SpatialRelator_14 [Requestor]
SpatialRelator_14_Supplier_7 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_15_Requestor_6 (input)
    -> SpatialRelator_15 [Requestor]
SpatialRelator_15_Supplier_6 (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_16_Requestor_6 (input)
    -> SpatialRelator_16 [Requestor]
SpatialRelator_16_Supplier_6 (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_17_Requestor_6 (input)
    -> SpatialRelator_17 [Requestor]
SpatialRelator_17_Supplier_6 (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_18_Requestor_6 (input)
    -> SpatialRelator_18 [Requestor]
SpatialRelator_18_Supplier_6 (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_19_Requestor_6 (input)
    -> SpatialRelator_19 [Requestor]
SpatialRelator_19_Supplier_6 (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_20_Requestor_6 (input)
    -> SpatialRelator_20 [Requestor]
SpatialRelator_20_Supplier_6 (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_21_Requestor_6 (input)
    -> SpatialRelator_21 [Requestor]
SpatialRelator_21_Supplier_6 (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_22_Requestor_5 (input)
    -> SpatialRelator_22 [Requestor]
SpatialRelator_22_Supplier_5 (input)
    -> SpatialRelator_22 [Supplier]
SpatialRelator_22
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_23_Requestor_5 (input)
    -> SpatialRelator_23 [Requestor]
SpatialRelator_23_Supplier_5 (input)
    -> SpatialRelator_23 [Supplier]
SpatialRelator_23
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_24_Requestor_5 (input)
    -> SpatialRelator_24 [Requestor]
SpatialRelator_24_Supplier_5 (input)
    -> SpatialRelator_24 [Supplier]
SpatialRelator_24
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_25_Requestor_5 (input)
    -> SpatialRelator_25 [Requestor]
SpatialRelator_25_Supplier_5 (input)
    -> SpatialRelator_25 [Supplier]
SpatialRelator_25
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_26_Requestor_5 (input)
    -> SpatialRelator_26 [Requestor]
SpatialRelator_26_Supplier_5 (input)
    -> SpatialRelator_26 [Supplier]
SpatialRelator_26
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_27_Requestor_4 (input)
    -> SpatialRelator_27 [Requestor]
SpatialRelator_27_Supplier_4 (input)
    -> SpatialRelator_27 [Supplier]
SpatialRelator_27
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_28_Requestor_4 (input)
    -> SpatialRelator_28 [Requestor]
SpatialRelator_28_Supplier_4 (input)
    -> SpatialRelator_28 [Supplier]
SpatialRelator_28
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_29_Requestor_4 (input)
    -> SpatialRelator_29 [Requestor]
SpatialRelator_29_Supplier_4 (input)
    -> SpatialRelator_29 [Supplier]
SpatialRelator_29
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_30_Requestor_4 (input)
    -> SpatialRelator_30 [Requestor]
SpatialRelator_30_Supplier_4 (input)
    -> SpatialRelator_30 [Supplier]
SpatialRelator_30
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_31_Requestor_4 (input)
    -> SpatialRelator_31 [Requestor]
SpatialRelator_31_Supplier_4 (input)
    -> SpatialRelator_31 [Supplier]
SpatialRelator_31
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_32_Requestor_4 (input)
    -> SpatialRelator_32 [Requestor]
SpatialRelator_32_Supplier_4 (input)
    -> SpatialRelator_32 [Supplier]
SpatialRelator_32
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_33_Requestor_4 (input)
    -> SpatialRelator_33 [Requestor]
SpatialRelator_33_Supplier_4 (input)
    -> SpatialRelator_33 [Supplier]
SpatialRelator_33
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_34_Requestor_4 (input)
    -> SpatialRelator_34 [Requestor]
SpatialRelator_34_Supplier_4 (input)
    -> SpatialRelator_34 [Supplier]
SpatialRelator_34
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_35_Requestor_3 (input)
    -> SpatialRelator_35 [Requestor]
SpatialRelator_35_Supplier_3 (input)
    -> SpatialRelator_35 [Supplier]
SpatialRelator_35
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_36_Requestor_2 (input)
    -> SpatialRelator_36 [Requestor]
SpatialRelator_36_Supplier_2 (input)
    -> SpatialRelator_36 [Supplier]
SpatialRelator_36
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_37_Requestor_2 (input)
    -> SpatialRelator_37 [Requestor]
SpatialRelator_37_Supplier_2 (input)
    -> SpatialRelator_37 [Supplier]
SpatialRelator_37
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_38_Requestor_2 (input)
    -> SpatialRelator_38 [Requestor]
SpatialRelator_38_Supplier_2 (input)
    -> SpatialRelator_38 [Supplier]
SpatialRelator_38
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_39_Requestor_2 (input)
    -> SpatialRelator_39 [Requestor]
SpatialRelator_39_Supplier_2 (input)
    -> SpatialRelator_39 [Supplier]
SpatialRelator_39
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_40_Requestor_2 (input)
    -> SpatialRelator_40 [Requestor]
SpatialRelator_40_Supplier_2 (input)
    -> SpatialRelator_40 [Supplier]
SpatialRelator_40
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_41_Requestor_2 (input)
    -> SpatialRelator_41 [Requestor]
SpatialRelator_41_Supplier_2 (input)
    -> SpatialRelator_41 [Supplier]
SpatialRelator_41
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_42_Requestor_2 (input)
    -> SpatialRelator_42 [Requestor]
SpatialRelator_42_Supplier_2 (input)
    -> SpatialRelator_42 [Supplier]
SpatialRelator_42
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_43_Requestor_2 (input)
    -> SpatialRelator_43 [Requestor]
SpatialRelator_43_Supplier_2 (input)
    -> SpatialRelator_43 [Supplier]
SpatialRelator_43
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_44_Requestor_2 (input)
    -> SpatialRelator_44 [Requestor]
SpatialRelator_44_Supplier_2 (input)
    -> SpatialRelator_44 [Supplier]
SpatialRelator_44
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_45_Requestor_2 (input)
    -> SpatialRelator_45 [Requestor]
SpatialRelator_45_Supplier_2 (input)
    -> SpatialRelator_45 [Supplier]
SpatialRelator_45
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_46_Requestor_2 (input)
    -> SpatialRelator_46 [Requestor]
SpatialRelator_46_Supplier_2 (input)
    -> SpatialRelator_46 [Supplier]
SpatialRelator_46
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_47_Requestor_2 (input)
    -> SpatialRelator_47 [Requestor]
SpatialRelator_47_Supplier_2 (input)
    -> SpatialRelator_47 [Supplier]
SpatialRelator_47
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_48_Requestor_2 (input)
    -> SpatialRelator_48 [Requestor]
SpatialRelator_48_Supplier_2 (input)
    -> SpatialRelator_48 [Supplier]
SpatialRelator_48
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_49_Requestor_2 (input)
    -> SpatialRelator_49 [Requestor]
SpatialRelator_49_Supplier_2 (input)
    -> SpatialRelator_49 [Supplier]
SpatialRelator_49
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_50_Requestor_2 (input)
    -> SpatialRelator_50 [Requestor]
SpatialRelator_50_Supplier_2 (input)
    -> SpatialRelator_50 [Supplier]
SpatialRelator_50
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_51_Requestor_2 (input)
    -> SpatialRelator_51 [Requestor]
SpatialRelator_51_Supplier_2 (input)
    -> SpatialRelator_51 [Supplier]
SpatialRelator_51
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_52_Requestor_2 (input)
    -> SpatialRelator_52 [Requestor]
SpatialRelator_52_Supplier_2 (input)
    -> SpatialRelator_52 [Supplier]
SpatialRelator_52
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_05

Parameters:
- LIST_ATTRS_TO_INCLUDE = _indices{}.z   # NO_EXPAND_LIST Indices{}.z

SpatialRelator_3_Requestor_6 (input)
    -> SpatialRelator_3 [Requestor]
SpatialRelator_3_Supplier_6 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_4_Requestor_6 (input)
    -> SpatialRelator_4 [Requestor]
SpatialRelator_4_Supplier_6 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_5_Requestor_6 (input)
    -> SpatialRelator_5 [Requestor]
SpatialRelator_5_Supplier_6 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_6_Requestor_6 (input)
    -> SpatialRelator_6 [Requestor]
SpatialRelator_6_Supplier_6 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_7_Requestor_6 (input)
    -> SpatialRelator_7 [Requestor]
SpatialRelator_7_Supplier_6 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_8_Requestor_5 (input)
    -> SpatialRelator_8 [Requestor]
SpatialRelator_8_Supplier_5 (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_9_Requestor_6 (input)
    -> SpatialRelator_9 [Requestor]
SpatialRelator_9_Supplier_6 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_10_Requestor_6 (input)
    -> SpatialRelator_10 [Requestor]
SpatialRelator_10_Supplier_6 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_11_Requestor_6 (input)
    -> SpatialRelator_11 [Requestor]
SpatialRelator_11_Supplier_6 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_12_Requestor_6 (input)
    -> SpatialRelator_12 [Requestor]
SpatialRelator_12_Supplier_6 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_13_Requestor_6 (input)
    -> SpatialRelator_13 [Requestor]
SpatialRelator_13_Supplier_6 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_14_Requestor_6 (input)
    -> SpatialRelator_14 [Requestor]
SpatialRelator_14_Supplier_6 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_15_Requestor_5 (input)
    -> SpatialRelator_15 [Requestor]
SpatialRelator_15_Supplier_5 (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_16_Requestor_5 (input)
    -> SpatialRelator_16 [Requestor]
SpatialRelator_16_Supplier_5 (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_17_Requestor_5 (input)
    -> SpatialRelator_17 [Requestor]
SpatialRelator_17_Supplier_5 (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_18_Requestor_5 (input)
    -> SpatialRelator_18 [Requestor]
SpatialRelator_18_Supplier_5 (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_19_Requestor_5 (input)
    -> SpatialRelator_19 [Requestor]
SpatialRelator_19_Supplier_5 (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_20_Requestor_5 (input)
    -> SpatialRelator_20 [Requestor]
SpatialRelator_20_Supplier_5 (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_21_Requestor_5 (input)
    -> SpatialRelator_21 [Requestor]
SpatialRelator_21_Supplier_5 (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_22_Requestor_4 (input)
    -> SpatialRelator_22 [Requestor]
SpatialRelator_22_Supplier_4 (input)
    -> SpatialRelator_22 [Supplier]
SpatialRelator_22
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_23_Requestor_4 (input)
    -> SpatialRelator_23 [Requestor]
SpatialRelator_23_Supplier_4 (input)
    -> SpatialRelator_23 [Supplier]
SpatialRelator_23
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_24_Requestor_4 (input)
    -> SpatialRelator_24 [Requestor]
SpatialRelator_24_Supplier_4 (input)
    -> SpatialRelator_24 [Supplier]
SpatialRelator_24
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_25_Requestor_4 (input)
    -> SpatialRelator_25 [Requestor]
SpatialRelator_25_Supplier_4 (input)
    -> SpatialRelator_25 [Supplier]
SpatialRelator_25
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_26_Requestor_4 (input)
    -> SpatialRelator_26 [Requestor]
SpatialRelator_26_Supplier_4 (input)
    -> SpatialRelator_26 [Supplier]
SpatialRelator_26
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_27_Requestor_3 (input)
    -> SpatialRelator_27 [Requestor]
SpatialRelator_27_Supplier_3 (input)
    -> SpatialRelator_27 [Supplier]
SpatialRelator_27
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_28_Requestor_3 (input)
    -> SpatialRelator_28 [Requestor]
SpatialRelator_28_Supplier_3 (input)
    -> SpatialRelator_28 [Supplier]
SpatialRelator_28
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_29_Requestor_3 (input)
    -> SpatialRelator_29 [Requestor]
SpatialRelator_29_Supplier_3 (input)
    -> SpatialRelator_29 [Supplier]
SpatialRelator_29
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_30_Requestor_3 (input)
    -> SpatialRelator_30 [Requestor]
SpatialRelator_30_Supplier_3 (input)
    -> SpatialRelator_30 [Supplier]
SpatialRelator_30
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_31_Requestor_3 (input)
    -> SpatialRelator_31 [Requestor]
SpatialRelator_31_Supplier_3 (input)
    -> SpatialRelator_31 [Supplier]
SpatialRelator_31
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_32_Requestor_3 (input)
    -> SpatialRelator_32 [Requestor]
SpatialRelator_32_Supplier_3 (input)
    -> SpatialRelator_32 [Supplier]
SpatialRelator_32
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_33_Requestor_3 (input)
    -> SpatialRelator_33 [Requestor]
SpatialRelator_33_Supplier_3 (input)
    -> SpatialRelator_33 [Supplier]
SpatialRelator_33
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_34_Requestor_3 (input)
    -> SpatialRelator_34 [Requestor]
SpatialRelator_34_Supplier_3 (input)
    -> SpatialRelator_34 [Supplier]
SpatialRelator_34
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_35_Requestor_2 (input)
    -> SpatialRelator_35 [Requestor]
SpatialRelator_35_Supplier_2 (input)
    -> SpatialRelator_35 [Supplier]
SpatialRelator_35
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_36_Requestor_1 (input)
    -> SpatialRelator_36 [Requestor]
SpatialRelator_36_Supplier_1 (input)
    -> SpatialRelator_36 [Supplier]
SpatialRelator_36
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_37_Requestor_1 (input)
    -> SpatialRelator_37 [Requestor]
SpatialRelator_37_Supplier_1 (input)
    -> SpatialRelator_37 [Supplier]
SpatialRelator_37
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_38_Requestor_1 (input)
    -> SpatialRelator_38 [Requestor]
SpatialRelator_38_Supplier_1 (input)
    -> SpatialRelator_38 [Supplier]
SpatialRelator_38
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_39_Requestor_1 (input)
    -> SpatialRelator_39 [Requestor]
SpatialRelator_39_Supplier_1 (input)
    -> SpatialRelator_39 [Supplier]
SpatialRelator_39
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_40_Requestor_1 (input)
    -> SpatialRelator_40 [Requestor]
SpatialRelator_40_Supplier_1 (input)
    -> SpatialRelator_40 [Supplier]
SpatialRelator_40
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_41_Requestor_1 (input)
    -> SpatialRelator_41 [Requestor]
SpatialRelator_41_Supplier_1 (input)
    -> SpatialRelator_41 [Supplier]
SpatialRelator_41
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_42_Requestor_1 (input)
    -> SpatialRelator_42 [Requestor]
SpatialRelator_42_Supplier_1 (input)
    -> SpatialRelator_42 [Supplier]
SpatialRelator_42
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_43_Requestor_1 (input)
    -> SpatialRelator_43 [Requestor]
SpatialRelator_43_Supplier_1 (input)
    -> SpatialRelator_43 [Supplier]
SpatialRelator_43
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_44_Requestor_1 (input)
    -> SpatialRelator_44 [Requestor]
SpatialRelator_44_Supplier_1 (input)
    -> SpatialRelator_44 [Supplier]
SpatialRelator_44
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_45_Requestor_1 (input)
    -> SpatialRelator_45 [Requestor]
SpatialRelator_45_Supplier_1 (input)
    -> SpatialRelator_45 [Supplier]
SpatialRelator_45
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_46_Requestor_1 (input)
    -> SpatialRelator_46 [Requestor]
SpatialRelator_46_Supplier_1 (input)
    -> SpatialRelator_46 [Supplier]
SpatialRelator_46
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_47_Requestor_1 (input)
    -> SpatialRelator_47 [Requestor]
SpatialRelator_47_Supplier_1 (input)
    -> SpatialRelator_47 [Supplier]
SpatialRelator_47
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_48_Requestor_1 (input)
    -> SpatialRelator_48 [Requestor]
SpatialRelator_48_Supplier_1 (input)
    -> SpatialRelator_48 [Supplier]
SpatialRelator_48
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_49_Requestor_1 (input)
    -> SpatialRelator_49 [Requestor]
SpatialRelator_49_Supplier_1 (input)
    -> SpatialRelator_49 [Supplier]
SpatialRelator_49
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_50_Requestor_1 (input)
    -> SpatialRelator_50 [Requestor]
SpatialRelator_50_Supplier_1 (input)
    -> SpatialRelator_50 [Supplier]
SpatialRelator_50
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_51_Requestor_1 (input)
    -> SpatialRelator_51 [Requestor]
SpatialRelator_51_Supplier_1 (input)
    -> SpatialRelator_51 [Supplier]
SpatialRelator_51
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_52_Requestor_1 (input)
    -> SpatialRelator_52 [Requestor]
SpatialRelator_52_Supplier_1 (input)
    -> SpatialRelator_52 [Supplier]
SpatialRelator_52
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_07

Parameters:
- LIST_ATTRS_TO_INCLUDE = _indices{}.z   # NO_EXPAND_LIST Indices{}.z

SpatialRelator_54_Requestor (input)
    -> SpatialRelator_54 [Requestor]
SpatialRelator_54_Supplier (input)
    -> SpatialRelator_54 [Supplier]
SpatialRelator_54
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_55_Requestor (input)
    -> SpatialRelator_55 [Requestor]
SpatialRelator_55_Supplier (input)
    -> SpatialRelator_55 [Supplier]
SpatialRelator_55
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_56_Requestor (input)
    -> SpatialRelator_56 [Requestor]
SpatialRelator_56_Supplier (input)
    -> SpatialRelator_56 [Supplier]
SpatialRelator_56
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_57_Requestor (input)
    -> SpatialRelator_57 [Requestor]
SpatialRelator_57_Supplier (input)
    -> SpatialRelator_57 [Supplier]
SpatialRelator_57
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_58_Requestor (input)
    -> SpatialRelator_58 [Requestor]
SpatialRelator_58_Supplier (input)
    -> SpatialRelator_58 [Supplier]
SpatialRelator_58
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_59_Requestor (input)
    -> SpatialRelator_59 [Requestor]
SpatialRelator_59_Supplier (input)
    -> SpatialRelator_59 [Supplier]
SpatialRelator_59
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_60_Requestor (input)
    -> SpatialRelator_60 [Requestor]
SpatialRelator_60_Supplier (input)
    -> SpatialRelator_60 [Supplier]
SpatialRelator_60
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_61_Requestor (input)
    -> SpatialRelator_61 [Requestor]
SpatialRelator_61_Supplier (input)
    -> SpatialRelator_61 [Supplier]
SpatialRelator_61
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_62_Requestor (input)
    -> SpatialRelator_62 [Requestor]
SpatialRelator_62_Supplier (input)
    -> SpatialRelator_62 [Supplier]
SpatialRelator_62
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_63_Requestor (input)
    -> SpatialRelator_63 [Requestor]
SpatialRelator_63_Supplier (input)
    -> SpatialRelator_63 [Supplier]
SpatialRelator_63
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_3_Requestor_8 (input)
    -> SpatialRelator_3 [Requestor]
SpatialRelator_3_Supplier_8 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_64_Requestor (input)
    -> SpatialRelator_64 [Requestor]
SpatialRelator_64_Supplier (input)
    -> SpatialRelator_64 [Supplier]
SpatialRelator_64
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_65_Requestor (input)
    -> SpatialRelator_65 [Requestor]
SpatialRelator_65_Supplier (input)
    -> SpatialRelator_65 [Supplier]
SpatialRelator_65
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_66_Requestor (input)
    -> SpatialRelator_66 [Requestor]
SpatialRelator_66_Supplier (input)
    -> SpatialRelator_66 [Supplier]
SpatialRelator_66
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_67_Requestor (input)
    -> SpatialRelator_67 [Requestor]
SpatialRelator_67_Supplier (input)
    -> SpatialRelator_67 [Supplier]
SpatialRelator_67
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_68_Requestor (input)
    -> SpatialRelator_68 [Requestor]
SpatialRelator_68_Supplier (input)
    -> SpatialRelator_68 [Supplier]
SpatialRelator_68
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_69_Requestor (input)
    -> SpatialRelator_69 [Requestor]
SpatialRelator_69_Supplier (input)
    -> SpatialRelator_69 [Supplier]
SpatialRelator_69
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_70_Requestor (input)
    -> SpatialRelator_70 [Requestor]
SpatialRelator_70_Supplier (input)
    -> SpatialRelator_70 [Supplier]
SpatialRelator_70
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_71_Requestor (input)
    -> SpatialRelator_71 [Requestor]
SpatialRelator_71_Supplier (input)
    -> SpatialRelator_71 [Supplier]
SpatialRelator_71
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_72_Requestor (input)
    -> SpatialRelator_72 [Requestor]
SpatialRelator_72_Supplier (input)
    -> SpatialRelator_72 [Supplier]
SpatialRelator_72
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_73_Requestor (input)
    -> SpatialRelator_73 [Requestor]
SpatialRelator_73_Supplier (input)
    -> SpatialRelator_73 [Supplier]
SpatialRelator_73
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_74_Requestor (input)
    -> SpatialRelator_74 [Requestor]
SpatialRelator_74_Supplier (input)
    -> SpatialRelator_74 [Supplier]
SpatialRelator_74
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_75_Requestor (input)
    -> SpatialRelator_75 [Requestor]
SpatialRelator_75_Supplier (input)
    -> SpatialRelator_75 [Supplier]
SpatialRelator_75
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_76_Requestor (input)
    -> SpatialRelator_76 [Requestor]
SpatialRelator_76_Supplier (input)
    -> SpatialRelator_76 [Supplier]
SpatialRelator_76
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_77_Requestor (input)
    -> SpatialRelator_77 [Requestor]
SpatialRelator_77_Supplier (input)
    -> SpatialRelator_77 [Supplier]
SpatialRelator_77
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_78_Requestor (input)
    -> SpatialRelator_78 [Requestor]
SpatialRelator_78_Supplier (input)
    -> SpatialRelator_78 [Supplier]
SpatialRelator_78
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_79_Requestor (input)
    -> SpatialRelator_79 [Requestor]
SpatialRelator_79_Supplier (input)
    -> SpatialRelator_79 [Supplier]
SpatialRelator_79
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_80_Requestor (input)
    -> SpatialRelator_80 [Requestor]
SpatialRelator_80_Supplier (input)
    -> SpatialRelator_80 [Supplier]
SpatialRelator_80
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_81_Requestor (input)
    -> SpatialRelator_81 [Requestor]
SpatialRelator_81_Supplier (input)
    -> SpatialRelator_81 [Supplier]
SpatialRelator_81
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_82_Requestor (input)
    -> SpatialRelator_82 [Requestor]
SpatialRelator_82_Supplier (input)
    -> SpatialRelator_82 [Supplier]
SpatialRelator_82
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_83_Requestor (input)
    -> SpatialRelator_83 [Requestor]
SpatialRelator_83_Supplier (input)
    -> SpatialRelator_83 [Supplier]
SpatialRelator_83
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_84_Requestor (input)
    -> SpatialRelator_84 [Requestor]
SpatialRelator_84_Supplier (input)
    -> SpatialRelator_84 [Supplier]
SpatialRelator_84
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_85_Requestor (input)
    -> SpatialRelator_85 [Requestor]
SpatialRelator_85_Supplier (input)
    -> SpatialRelator_85 [Supplier]
SpatialRelator_85
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_86_Requestor (input)
    -> SpatialRelator_86 [Requestor]
SpatialRelator_86_Supplier (input)
    -> SpatialRelator_86 [Supplier]
SpatialRelator_86
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_87_Requestor (input)
    -> SpatialRelator_87 [Requestor]
SpatialRelator_87_Supplier (input)
    -> SpatialRelator_87 [Supplier]
SpatialRelator_87
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_88_Requestor (input)
    -> SpatialRelator_88 [Requestor]
SpatialRelator_88_Supplier (input)
    -> SpatialRelator_88 [Supplier]
SpatialRelator_88
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_89_Requestor (input)
    -> SpatialRelator_89 [Requestor]
SpatialRelator_89_Supplier (input)
    -> SpatialRelator_89 [Supplier]
SpatialRelator_89
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_90_Requestor (input)
    -> SpatialRelator_90 [Requestor]
SpatialRelator_90_Supplier (input)
    -> SpatialRelator_90 [Supplier]
SpatialRelator_90
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_91_Requestor (input)
    -> SpatialRelator_91 [Requestor]
SpatialRelator_91_Supplier (input)
    -> SpatialRelator_91 [Supplier]
SpatialRelator_91
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_92_Requestor (input)
    -> SpatialRelator_92 [Requestor]
SpatialRelator_92_Supplier (input)
    -> SpatialRelator_92 [Supplier]
SpatialRelator_92
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_93_Requestor (input)
    -> SpatialRelator_93 [Requestor]
SpatialRelator_93_Supplier (input)
    -> SpatialRelator_93 [Supplier]
SpatialRelator_93
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_53_Requestor (input)
    -> SpatialRelator_53 [Requestor]
SpatialRelator_53_Supplier (input)
    -> SpatialRelator_53 [Supplier]
SpatialRelator_53
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_94_Requestor (input)
    -> SpatialRelator_94 [Requestor]
SpatialRelator_94_Supplier (input)
    -> SpatialRelator_94 [Supplier]
SpatialRelator_94
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_95_Requestor (input)
    -> SpatialRelator_95 [Requestor]
SpatialRelator_95_Supplier (input)
    -> SpatialRelator_95 [Supplier]
SpatialRelator_95
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_96_Requestor (input)
    -> SpatialRelator_96 [Requestor]
SpatialRelator_96_Supplier (input)
    -> SpatialRelator_96 [Supplier]
SpatialRelator_96
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_97_Requestor (input)
    -> SpatialRelator_97 [Requestor]
SpatialRelator_97_Supplier (input)
    -> SpatialRelator_97 [Supplier]
SpatialRelator_97
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_98_Requestor (input)
    -> SpatialRelator_98 [Requestor]
SpatialRelator_98_Supplier (input)
    -> SpatialRelator_98 [Supplier]
SpatialRelator_98
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_99_Requestor (input)
    -> SpatialRelator_99 [Requestor]
SpatialRelator_99_Supplier (input)
    -> SpatialRelator_99 [Supplier]
SpatialRelator_99
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_100_Requestor (input)
    -> SpatialRelator_100 [Requestor]
SpatialRelator_100_Supplier (input)
    -> SpatialRelator_100 [Supplier]
SpatialRelator_100
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_101_Requestor (input)
    -> SpatialRelator_101 [Requestor]
SpatialRelator_101_Supplier (input)
    -> SpatialRelator_101 [Supplier]
SpatialRelator_101
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_102_Requestor (input)
    -> SpatialRelator_102 [Requestor]
SpatialRelator_102_Supplier (input)
    -> SpatialRelator_102 [Supplier]
SpatialRelator_102
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_02

Parameters:
- LIST_ATTRS_TO_INCLUDE = _indices{}.z   # NO_EXPAND_LIST Indices{}.z

SpatialRelator_7_Requestor_1 (input)
    -> SpatialRelator_7 [Requestor]
SpatialRelator_7_Supplier_1 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_2_Requestor_1 (input)
    -> SpatialRelator_2 [Requestor]
SpatialRelator_2_Supplier_1 (input)
    -> SpatialRelator_2 [Supplier]
SpatialRelator_2
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_3_Requestor_1 (input)
    -> SpatialRelator_3 [Requestor]
SpatialRelator_3_Supplier_1 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_4_Requestor_1 (input)
    -> SpatialRelator_4 [Requestor]
SpatialRelator_4_Supplier_1 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_5_Requestor_1 (input)
    -> SpatialRelator_5 [Requestor]
SpatialRelator_5_Supplier_1 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_6_Requestor_1 (input)
    -> SpatialRelator_6 [Requestor]
SpatialRelator_6_Supplier_1 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_9_Requestor_1 (input)
    -> SpatialRelator_9 [Requestor]
SpatialRelator_9_Supplier_1 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_10_Requestor_1 (input)
    -> SpatialRelator_10 [Requestor]
SpatialRelator_10_Supplier_1 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_11_Requestor_1 (input)
    -> SpatialRelator_11 [Requestor]
SpatialRelator_11_Supplier_1 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_12_Requestor_1 (input)
    -> SpatialRelator_12 [Requestor]
SpatialRelator_12_Supplier_1 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_14_Requestor_1 (input)
    -> SpatialRelator_14 [Requestor]
SpatialRelator_14_Supplier_1 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_15_Requestor (input)
    -> SpatialRelator_15 [Requestor]
SpatialRelator_15_Supplier (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_16_Requestor (input)
    -> SpatialRelator_16 [Requestor]
SpatialRelator_16_Supplier (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_17_Requestor (input)
    -> SpatialRelator_17 [Requestor]
SpatialRelator_17_Supplier (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_20_Requestor (input)
    -> SpatialRelator_20 [Requestor]
SpatialRelator_20_Supplier (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_21_Requestor (input)
    -> SpatialRelator_21 [Requestor]
SpatialRelator_21_Supplier (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_13_Requestor_1 (input)
    -> SpatialRelator_13 [Requestor]
SpatialRelator_13_Supplier_1 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_18_Requestor (input)
    -> SpatialRelator_18 [Requestor]
SpatialRelator_18_Supplier (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_19_Requestor (input)
    -> SpatialRelator_19 [Requestor]
SpatialRelator_19_Supplier (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> SpatialRelator_Output (output)
SpatialRelator_Output (output)

FME custom transformer Transformador_3

Parameters:
- LIST_ATTRS_TO_INCLUDE = _indices{}.z   # NO_EXPAND_LIST Indices{}.z

SpatialRelator_28_Requestor_1 (input)
    -> SpatialRelator_28 [Requestor]
SpatialRelator_28_Supplier_1 (input)
    -> SpatialRelator_28 [Supplier]
SpatialRelator_28
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_29_Requestor_1 (input)
    -> SpatialRelator_29 [Requestor]
SpatialRelator_29_Supplier_1 (input)
    -> SpatialRelator_29 [Supplier]
SpatialRelator_29
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_30_Requestor_1 (input)
    -> SpatialRelator_30 [Requestor]
SpatialRelator_30_Supplier_1 (input)
    -> SpatialRelator_30 [Supplier]
SpatialRelator_30
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_3_Requestor_4 (input)
    -> SpatialRelator_3 [Requestor]
SpatialRelator_3_Supplier_4 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_4_Requestor_4 (input)
    -> SpatialRelator_4 [Requestor]
SpatialRelator_4_Supplier_4 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_5_Requestor_4 (input)
    -> SpatialRelator_5 [Requestor]
SpatialRelator_5_Supplier_4 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_6_Requestor_4 (input)
    -> SpatialRelator_6 [Requestor]
SpatialRelator_6_Supplier_4 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_7_Requestor_4 (input)
    -> SpatialRelator_7 [Requestor]
SpatialRelator_7_Supplier_4 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_8_Requestor_3 (input)
    -> SpatialRelator_8 [Requestor]
SpatialRelator_8_Supplier_3 (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_9_Requestor_4 (input)
    -> SpatialRelator_9 [Requestor]
SpatialRelator_9_Supplier_4 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_10_Requestor_4 (input)
    -> SpatialRelator_10 [Requestor]
SpatialRelator_10_Supplier_4 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_11_Requestor_4 (input)
    -> SpatialRelator_11 [Requestor]
SpatialRelator_11_Supplier_4 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_12_Requestor_4 (input)
    -> SpatialRelator_12 [Requestor]
SpatialRelator_12_Supplier_4 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_13_Requestor_4 (input)
    -> SpatialRelator_13 [Requestor]
SpatialRelator_13_Supplier_4 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_14_Requestor_4 (input)
    -> SpatialRelator_14 [Requestor]
SpatialRelator_14_Supplier_4 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_15_Requestor_3 (input)
    -> SpatialRelator_15 [Requestor]
SpatialRelator_15_Supplier_3 (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_16_Requestor_3 (input)
    -> SpatialRelator_16 [Requestor]
SpatialRelator_16_Supplier_3 (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_17_Requestor_3 (input)
    -> SpatialRelator_17 [Requestor]
SpatialRelator_17_Supplier_3 (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_18_Requestor_3 (input)
    -> SpatialRelator_18 [Requestor]
SpatialRelator_18_Supplier_3 (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_19_Requestor_3 (input)
    -> SpatialRelator_19 [Requestor]
SpatialRelator_19_Supplier_3 (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_20_Requestor_3 (input)
    -> SpatialRelator_20 [Requestor]
SpatialRelator_20_Supplier_3 (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_21_Requestor_3 (input)
    -> SpatialRelator_21 [Requestor]
SpatialRelator_21_Supplier_3 (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_22_Requestor_2 (input)
    -> SpatialRelator_22 [Requestor]
SpatialRelator_22_Supplier_2 (input)
    -> SpatialRelator_22 [Supplier]
SpatialRelator_22
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_32_Requestor_1 (input)
    -> SpatialRelator_32 [Requestor]
SpatialRelator_32_Supplier_1 (input)
    -> SpatialRelator_32 [Supplier]
SpatialRelator_32
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_34_Requestor_1 (input)
    -> SpatialRelator_34 [Requestor]
SpatialRelator_34_Supplier_1 (input)
    -> SpatialRelator_34 [Supplier]
SpatialRelator_34
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_23_Requestor_2 (input)
    -> SpatialRelator_23 [Requestor]
SpatialRelator_23_Supplier_2 (input)
    -> SpatialRelator_23 [Supplier]
SpatialRelator_23
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_24_Requestor_2 (input)
    -> SpatialRelator_24 [Requestor]
SpatialRelator_24_Supplier_2 (input)
    -> SpatialRelator_24 [Supplier]
SpatialRelator_24
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_25_Requestor_2 (input)
    -> SpatialRelator_25 [Requestor]
SpatialRelator_25_Supplier_2 (input)
    -> SpatialRelator_25 [Supplier]
SpatialRelator_25
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_26_Requestor_2 (input)
    -> SpatialRelator_26 [Requestor]
SpatialRelator_26_Supplier_2 (input)
    -> SpatialRelator_26 [Supplier]
SpatialRelator_26
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_27_Requestor_1 (input)
    -> SpatialRelator_27 [Requestor]
SpatialRelator_27_Supplier_1 (input)
    -> SpatialRelator_27 [Supplier]
SpatialRelator_27
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_31_Requestor_1 (input)
    -> SpatialRelator_31 [Requestor]
SpatialRelator_31_Supplier_1 (input)
    -> SpatialRelator_31 [Supplier]
SpatialRelator_31
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_33_Requestor_1 (input)
    -> SpatialRelator_33 [Requestor]
SpatialRelator_33_Supplier_1 (input)
    -> SpatialRelator_33 [Supplier]
SpatialRelator_33
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_35_Requestor (input)
    -> SpatialRelator_35 [Requestor]
SpatialRelator_35_Supplier (input)
    -> SpatialRelator_35 [Supplier]
SpatialRelator_35
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)

FME custom transformer Transformador_03

Parameters:
- LIST_ATTRS_TO_INCLUDE = _indices{}.z   # NO_EXPAND_LIST Indices{}.z

SpatialRelator_8_Requestor_1 (input)
    -> SpatialRelator_8 [Requestor]
SpatialRelator_8_Supplier_1 (input)
    -> SpatialRelator_8 [Supplier]
SpatialRelator_8
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_5_Requestor_2 (input)
    -> SpatialRelator_5 [Requestor]
SpatialRelator_5_Supplier_2 (input)
    -> SpatialRelator_5 [Supplier]
SpatialRelator_5
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_9_Requestor_2 (input)
    -> SpatialRelator_9 [Requestor]
SpatialRelator_9_Supplier_2 (input)
    -> SpatialRelator_9 [Supplier]
SpatialRelator_9
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_14_Requestor_2 (input)
    -> SpatialRelator_14 [Requestor]
SpatialRelator_14_Supplier_2 (input)
    -> SpatialRelator_14 [Supplier]
SpatialRelator_14
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_19_Requestor_1 (input)
    -> SpatialRelator_19 [Requestor]
SpatialRelator_19_Supplier_1 (input)
    -> SpatialRelator_19 [Supplier]
SpatialRelator_19
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_12_Requestor_2 (input)
    -> SpatialRelator_12 [Requestor]
SpatialRelator_12_Supplier_2 (input)
    -> SpatialRelator_12 [Supplier]
SpatialRelator_12
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_17_Requestor_1 (input)
    -> SpatialRelator_17 [Requestor]
SpatialRelator_17_Supplier_1 (input)
    -> SpatialRelator_17 [Supplier]
SpatialRelator_17
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_22_Requestor (input)
    -> SpatialRelator_22 [Requestor]
SpatialRelator_22_Supplier (input)
    -> SpatialRelator_22 [Supplier]
SpatialRelator_22
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_3_Requestor_2 (input)
    -> SpatialRelator_3 [Requestor]
SpatialRelator_3_Supplier_2 (input)
    -> SpatialRelator_3 [Supplier]
SpatialRelator_3
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_6_Requestor_2 (input)
    -> SpatialRelator_6 [Requestor]
SpatialRelator_6_Supplier_2 (input)
    -> SpatialRelator_6 [Supplier]
SpatialRelator_6
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_10_Requestor_2 (input)
    -> SpatialRelator_10 [Requestor]
SpatialRelator_10_Supplier_2 (input)
    -> SpatialRelator_10 [Supplier]
SpatialRelator_10
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_15_Requestor_1 (input)
    -> SpatialRelator_15 [Requestor]
SpatialRelator_15_Supplier_1 (input)
    -> SpatialRelator_15 [Supplier]
SpatialRelator_15
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_20_Requestor_1 (input)
    -> SpatialRelator_20 [Requestor]
SpatialRelator_20_Supplier_1 (input)
    -> SpatialRelator_20 [Supplier]
SpatialRelator_20
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_18_Requestor_1 (input)
    -> SpatialRelator_18 [Requestor]
SpatialRelator_18_Supplier_1 (input)
    -> SpatialRelator_18 [Supplier]
SpatialRelator_18
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_23_Requestor (input)
    -> SpatialRelator_23 [Requestor]
SpatialRelator_23_Supplier (input)
    -> SpatialRelator_23 [Supplier]
SpatialRelator_23
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_4_Requestor_2 (input)
    -> SpatialRelator_4 [Requestor]
SpatialRelator_4_Supplier_2 (input)
    -> SpatialRelator_4 [Supplier]
SpatialRelator_4
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
SpatialRelator_7_Requestor_2 (input)
    -> SpatialRelator_7 [Requestor]
SpatialRelator_7_Supplier_2 (input)
    -> SpatialRelator_7 [Supplier]
SpatialRelator_7
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_11_Requestor_2 (input)
    -> SpatialRelator_11 [Requestor]
SpatialRelator_11_Supplier_2 (input)
    -> SpatialRelator_11 [Supplier]
SpatialRelator_11
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_16_Requestor_1 (input)
    -> SpatialRelator_16 [Requestor]
SpatialRelator_16_Supplier_1 (input)
    -> SpatialRelator_16 [Supplier]
SpatialRelator_16
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_21_Requestor_1 (input)
    -> SpatialRelator_21 [Requestor]
SpatialRelator_21_Supplier_1 (input)
    -> SpatialRelator_21 [Supplier]
SpatialRelator_21
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_24_Requestor (input)
    -> SpatialRelator_24 [Requestor]
SpatialRelator_24_Supplier (input)
    -> SpatialRelator_24 [Supplier]
SpatialRelator_24
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_26_Requestor (input)
    -> SpatialRelator_26 [Requestor]
SpatialRelator_26_Supplier (input)
    -> SpatialRelator_26 [Supplier]
SpatialRelator_26
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_25_Requestor (input)
    -> SpatialRelator_25 [Requestor]
SpatialRelator_25_Supplier (input)
    -> SpatialRelator_25 [Supplier]
SpatialRelator_25
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
SpatialRelator_13_Requestor_2 (input)
    -> SpatialRelator_13 [Requestor]
SpatialRelator_13_Supplier_2 (input)
    -> SpatialRelator_13 [Supplier]
SpatialRelator_13
    AGGREGATE_HANDLING = No
    CALC_CARD = No
    CURVE_BOUNDARY_RULE_PARAM = Default Rule
    LIST_ATTRS_TO_INCLUDE = $(LIST_ATTRS_TO_INCLUDE)
    LIST_NAME = _relationships
    PREDICATES = CONTAINS
    SUCCESS_ATTR = _related_candidates
    -> Output (output)
Output (output)
